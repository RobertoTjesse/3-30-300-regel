FME workspace 30_2025.fmw

Creator_2
    GEOMTYPE = Geometry Object
    NUM = 1
    CREATED -> FeatureReader [INITIATOR]
FeatureReader
    ATTRIBUTES =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
    ATTR_ACCUM_MODE = Only Use Result
    CLIP_TO_ENVELOPE = NO
    COMBINE_GEOM = Use Result
    DATASET = $(FME_MF_DIR_ENCODED)fme input\Panden\wijkenbuurten_2023.gpkg
    FEATURETYPES = wijken
    FORMAT = OGCGEOPACKAGE
    GEOMETRY_TYPES = buurten,""",fme_area""",gemeenten,""",fme_area""",wijken,""",fme_area"""
    INTERACT = NONE
    OGCGEOPACKAGE_ENCODE_FEATURE_TYPE_AND_ATTR_NAMES = YES
    OGCGEOPACKAGE_ENFORCE_FOREIGN_KEY_INTEGRITY = YES
    OGCGEOPACKAGE_EXPOSE_PRIMARY_KEY_ATTRIBUTE = YES
    OGCGEOPACKAGE_OPEN_SINGLE_RASTER_AS_SUBDATASET = YES
    OGCGEOPACKAGE_QUERY_FEATURE_TYPES_FOR_MERGE_FILTERS = Yes
    OGCGEOPACKAGE_READER_REPLACE_INVALID_CHARS = NO
    OGCGEOPACKAGE_READ_BOOLEANS_AS_YES_NO = YES
    OGCGEOPACKAGE_READ_NULLS = YES
    OGCGEOPACKAGE_USE_SEARCH_ENVELOPE = NO
    ORDER_RESULTS = No
    OUTPUT_ADD_SCHEMA_ATTRIBUTES = NO
    OUTPUT_FEATURES_DISPLAY = Schema and Data Features
    WHERE = "gemeentenaam"='Hendrik-Ido-Ambacht'
    wijken -> SQLExecutor [INITIATOR]
    wijken -> FeatureJoiner [LEFT]
SQLExecutor
    COMBINE_ATTRS = Result Attributes Only
    COMBINE_GEOM = Result Geometry Only
    DATASET = sql_geo
    FORMAT = MSSQL_SPATIAL
    MSSQL_SPATIAL_APPLICATION_INTENT = ReadWrite
    MSSQL_SPATIAL_COMMAND_TIMEOUT = 200
    MSSQL_SPATIAL_CREATE_FEATURE_TABLES_FROM_DATA = Yes
    MSSQL_SPATIAL_NAMED_CONNECTION = sql_geo
    MSSQL_SPATIAL_QUERY_FEATURE_TYPES_FOR_MERGE_FILTERS = Yes
    OUTPUT_FEATURES = DATA_ONLY
    SQL_STATEMENT:
      WITH wijk_geom AS (
        SELECT
          wijkcode,
          SHAPE AS wijk_shape
        FROM GRENZEN.CBS_WIJKKAART_2022_VERSIE3
        WHERE wijkcode = '@Value(wijkcode)'
      ),

      bomen_in_wijk AS (
        SELECT
          b.CROWN_AREA
        FROM BODEM.BOMEN_KRONEN b
        JOIN wijk_geom w
          ON b.SHAPE.STIntersects(w.wijk_shape) = 1
      )

      SELECT
        '@Value(wijkcode)' AS wijkcode,
        SUM(CROWN_AREA) AS totaal_kroonoppervlak_m2
      FROM bomen_in_wijk;
    RESULT -> AttributeExposer
AttributeExposer
    ATTR_TABLE = wijkcode,,totaal_kroonoppervlak_m2,
    -> FeatureJoiner [RIGHT]
FeatureJoiner
    ATTR_CONFLICT_RES_LOOKUP = USE_LEFT
    GEOMETRY_HANDLING_LOOKUP = USE_LEFT
    JOIN_KEYS = wijkcode wijkcode AUTO
    JOIN_MODE = Inner
    ATTR_CONFLICT_RES = Prefer Left
    GEOMETRY_HANDLING = Prefer Left
    JOINED -> AttributeManager_2
AttributeManager_2
    ATTR_TABLE:
      SET_TO Percentage groen (real64) = @Evaluate((@Value(totaal_kroonoppervlak_m2)/100)/@Value(oppervlakte_land_in_ha))
      SET_TO

Bookmark: slome analyse
Creator
    GEOMTYPE = Geometry Object
    NUM = 1
    CREATED -> FeatureReader_5 [INITIATOR]
StatisticsCalculator
    ATTR_ACCUM_MODE = All
    CALCULATION_MODE = NUMERIC
    FEAT_STATS = crown_area,NUMERIC_MODE,,,,SUM,,,,,,,,,
    GROUP_BY = wijkcode
    SUMMARY -> FeatureMerger [SUPPLIER]
FeatureMerger
    ATTR_ACCUM_MODE = Merge Supplier
    ATTR_CONFLICT_RES_LOOKUP = REQUESTOR_IF_CONFLICT
    GROUP_BY = wijkcode
    IGNORE_NULLS = No
    JOIN_KEYS = 1 1 AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> AttributeManager
AttributeManager
    ATTR_TABLE:
      SET_TO oppervlakte_boom_in_ha (real64) = @Evaluate(@Value(crown_area.sum)/10000)
      SET_TO percentage_groen_land (real64) = @Evaluate(@Value(crown_area.sum)*100/((@Value(oppervlakte_land_in_ha)*10000)))
      REMOVE crown_area (real64)
      REMOVE _related_suppliers (uint32)
      REMOVE crown_area.sum (real64)

Bookmark: PDOK - Wijken, buurten, gemeenten
FeatureReader_5
    ATTRIBUTES =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
    ATTR_ACCUM_MODE = Only Use Result
    CLIP_TO_ENVELOPE = NO
    COMBINE_GEOM = Use Result
    DATASET = $(FME_MF_DIR_ENCODED)fme input\Panden\wijkenbuurten_2023.gpkg
    FEATURETYPES = wijken
    FORMAT = OGCGEOPACKAGE
    GEOMETRY_TYPES = buurten,"""geom,fme_area""",gemeenten,"""geom,fme_area""",wijken,"""geom,fme_area"""
    INITIATOR_FIRST_OUTPUT = default
    INTERACT = NONE
    OGCGEOPACKAGE_ENCODE_FEATURE_TYPE_AND_ATTR_NAMES = YES
    OGCGEOPACKAGE_ENFORCE_FOREIGN_KEY_INTEGRITY = YES
    OGCGEOPACKAGE_EXPOSE_PRIMARY_KEY_ATTRIBUTE = YES
    OGCGEOPACKAGE_OPEN_SINGLE_RASTER_AS_SUBDATASET = YES
    OGCGEOPACKAGE_QUERY_FEATURE_TYPES_FOR_MERGE_FILTERS = Yes
    OGCGEOPACKAGE_READER_REPLACE_INVALID_CHARS = NO
    OGCGEOPACKAGE_READ_BOOLEANS_AS_YES_NO = YES
    OGCGEOPACKAGE_READ_NULLS = YES
    OGCGEOPACKAGE_USE_SEARCH_ENVELOPE = NO
    ORDER_RESULTS = No
    OUTPUT_ADD_SCHEMA_ATTRIBUTES = NO
    OUTPUT_FEATURES_DISPLAY = Schema and Data Features
    WHERE = "gemeentenaam"='Hendrik-Ido-Ambacht'
    wijken -> FeatureReader_2 [INITIATOR]
    wijken -> FeatureReader_4 [INITIATOR]
    wijken -> FeatureReader_3 [INITIATOR]
    wijken -> AttributeKeeper

Bookmark: Bomen
FeatureReader_3
    ATTRIBUTES = BODEM.BOMEN_CENTERPOINTS,"OBJECTID,id,stem_id,tree_id,sys_period,dataset,date,method,quality,accuracy,accuracy_metadata,transaction_id,current_status,status_date",BODEM.BOMEN_KRONEN,"OBJECTID,id,tree_id,valid_period,sys_period,tile_name,current_status,status_date,status_source_id,management_form,management_form_dataset,management_form_date,management_form_method,management_form_quality,crown_area,crown_diameter,crown_dataset,crown_date,crown_method,crown_quality,height,height_dataset,height_date,height_method,height_quality,undergrowth_cover,undergrowth_dataset,undergrowth_date,undergrowth_method,undergrowth_quality,Geo_afgeschermd.BODEM.BOMEN_KRONEN.fid,Shape.STArea(),Shape.STLength()"
    ATTR_ACCUM_MODE = Only Use Result
    CLIP_TO_ENVELOPE = NO
    COMBINE_GEOM = Use Result
    DATASET = bomen
    FEATURETYPES = BODEM.BOMEN_KRONEN BODEM.BOMEN_CENTERPOINTS
    FORMAT = GEODATABASE_SDE
    GEODATABASE_SDE_ALIAS_MODE = NONE
    GEODATABASE_SDE_CACHE_MULTIPATCH_TEXTURES = yes
    GEODATABASE_SDE_CHECK_SIMPLE_GEOM = no
    GEODATABASE_SDE_CREATE_FEATURE_TABLES_FROM_DATA = Yes
    GEODATABASE_SDE_DISABLE_FEATURE_DATASET_ATTRIBUTE = Yes
    GEODATABASE_SDE_FEATURE_READ_MODE = Features
    GEODATABASE_SDE_IGNORE_NETWORK_INFO = yes
    GEODATABASE_SDE_IGNORE_RELATIONSHIP_INFO = yes
    GEODATABASE_SDE_MERGE_FEAT_LINKED_ANNOS = no
    GEODATABASE_SDE_NAMED_CONNECTION = bomen
    GEODATABASE_SDE_PERSISTENT_CONNECTION = no
    GEODATABASE_SDE_QUERY_FEATURE_TYPES_FOR_MERGE_FILTERS = Yes
    GEODATABASE_SDE_READ_THREE_POINT_ARCS = no
    GEODATABASE_SDE_READ_VERSION_DIFFERENCES = NO
    GEODATABASE_SDE_REMOVE_FEATURE_DATASET = NO
    GEODATABASE_SDE_REMOVE_TABLE_QUALIFIER = NO
    GEODATABASE_SDE_RESOLVE_DOMAINS = no
    GEODATABASE_SDE_RESOLVE_SUBTYPE_NAMES = yes
    GEODATABASE_SDE_SIMPLE_DONUT_GEOMETRY = no
    GEODATABASE_SDE_SPLIT_COMPLEX_ANNOS = no
    GEODATABASE_SDE_SPLIT_COMPLEX_EDGES = no
    GEODATABASE_SDE_SPLIT_MULTI_PART_ANNOS = no
    GEODATABASE_SDE_STRIP_GUID_GLOBALID_BRACES = no
    GEODATABASE_SDE_TRANSLATE_SPATIAL_DATA_ONLY = no
    GEODATABASE_SDE_USE_SEARCH_ENVELOPE = NO
    GEOMETRY_TYPES = BODEM.BOMEN_CENTERPOINTS,"""SHAPE,fme_point""",BODEM.BOMEN_KRONEN,"""Shape,fme_area"""
    INITIATOR_FIRST_OUTPUT = default
    INTERACT = NONE
    ORDER_RESULTS = No
    OUTPUT_ADD_SCHEMA_ATTRIBUTES = NO
    OUTPUT_FEATURES_DISPLAY = Schema and Data Features
    BODEM.BOMEN_KRONEN -> AttributeKeeper_2
    BODEM.BOMEN_KRONEN -> FeatureReader_3_BODEM.BOMEN_KRONEN
    BODEM.BOMEN_CENTERPOINTS -> FeatureReader_3_BODEM.BOMEN_CENTERPOINTS

Bookmark: DATA BRONNEN _ Hendrik-Ido-Ambacht JAAR 2023
AttributeKeeper_2
    CREATE_BULK_MODE_FEATURES = NO
    KEEP_ATTRS = crown_area
    -> SpatialRelator [Requestor]
FeatureReader_3_BODEM.BOMEN_KRONEN: Inspector
FeatureReader_3_BODEM.BOMEN_CENTERPOINTS: Inspector
AttributeKeeper
    CREATE_BULK_MODE_FEATURES = NO
    KEEP_ATTRS = gemeentecode,gemeentenaam,oppervlakte_land_in_ha,oppervlakte_totaal_in_ha,oppervlakte_water_in_ha,wijkcode,wijknaam
    -> Sampler
    -> SpatialRelator [Supplier]
SpatialRelator
    AGGREGATE_HANDLING = Yes
    ATTR_ACCUM_MODE = Merge Supplier
    ATTR_CONFLICT_RES = Use Requestor
    CALC_CARD = No
    CURVE_BOUNDARY_RULE_PARAM = Default Rule
    IGNORE_NULLS = Yes
    PREDICATES = WITHIN
    SUCCESS_ATTR = _related_suppliers
    -> StatisticsCalculator
Sampler
    MODE = ORIGINAL
    RATE = 1
    SAMPLE_TYPE_MULTIPLIER = -1
    SAMPLE_MODE = No
    SAMPLE_TYPE_LONG = First N Features
    SAMPLED -> FeatureMerger [REQUESTOR]
TestFilter
    DEFAULT_VALUE = <UNFILTERED>
    PASSED_TEST_GROUP_OUTPUT = FIRST
    TEST_LIST:
      "BOOL_OP,OR,COMPOSITE_TEST,""""""1 OR 2"""""",TEST_CLAUSE,TEST @Value(type) = meer, plas
      TEST @Value(type) = waterloop",@Value(type) = meer, plas

Bookmark: Panden Verblijfobjecten
FeatureReader_2 [off]
    ATTRIBUTES = Pand_2021_adres,"OBJECTID,Adres,bouwperiode,CBScode,Gemeente,identificatie,bouwjaar,officieel,status,begindatum,einddatum,documentdatum,documentnummer,aanduidinginonderzoek,aanduidingrecordcorrectie,aanduidingrecordinactief,Status_bestaand,Pand_oppervlakte,pandid,huisnummer,postcode,openbareruimtenaam,woonplaatsnaam,Aantal_vbo,Vloeropp_totaal,Vloeropp_bijeenkomst,Vloeropp_gezondheidszorg,Vloeropp_industrie,Vloeropp_kantoor,Vloeropp_onderwijs,Vloeropp_voorzieningen,Vloeropp_werk,Vloeropp_winkel,Vloeropp_woon,Verh_opp_pand_vloer,Shape_Length,Shape_Area",Pand_2022_adres,"OBJECTID,identificatie,Adres,openbareruimtenaam,huisnummer_start,huisnummer_eind,postcode,woonplaatsnaam,Gemeente,CBScode,Aantal_vbo,begindatum,einddatum,bouwjaar,bouwperiode,status,Status_bestaand,Pand_oppervlakte,Vloeropp_totaal,Vloeropp_bijeenkomst,Vloeropp_gezondheidszorg,Vloeropp_industrie,Vloeropp_kantoor,Vloeropp_onderwijs,Vloeropp_winkel,Vloeropp_woon,Vloeropp_cel,Vloeropp_overig,Vloeropp_logies,Vloeropp_sport,Verh_opp_pand_vloer,SHAPE_Length,SHAPE_Area",Pand_2023_adres,"OBJECTID,Adres,huisnummer_start,huisnummer_eind,bouwperiode,CBScode,Gemeente,einddatum,begindatum,identificatie,bouwjaar,status,Pand_oppervlakte,postcode,openbareruimtenaam,woonplaatsnaam,Aantal_vbo,Aantal_woningen,Vloeropp_totaal,Vloeropp_bijeenkomst,Vloeropp_gezondheidszorg,Vloeropp_industrie,Vloeropp_kantoor,Vloeropp_onderwijs,Vloeropp_winkel,Vloeropp_woon,Vloeropp_cel,Vloeropp_overig,Vloeropp_logies,Vloeropp_sport,Verh_opp_pand_vloer,Status_bestaand,Shape_Length,Shape_Area",Pand_2024,"OBJECTID,CBScode,Gemeente,jaar_einde,einddatum,begindatum,identificatie,voorkomenidentificatie,bouwjaar,geconstateerd,status,begingeldigheid,eindgeldigheid,documentdatum,documentnummer,tijdstipregistratie,eindregistratie,tijdstipregistratielv,tijdstipeindregistratielv,Status_bestaand,SHAPE_Length,SHAPE_Area",Pand_2024_adres,"OBJECTID,Adres,huisnummer_start,huisnummer_eind,bouwperiode,CBScode,Gemeente,einddatum,begindatum,identificatie,voorkomenidentificatie,bouwjaar,geconstateerd,status,begingeldigheid,eindgeldigheid,documentdatum,documentnummer,tijdstipregistratie,eindregistratie,tijdstipregistratielv,tijdstipeindregistratielv,Pand_oppervlakte,postcode,openbareruimtenaam,woonplaatsnaam,Aantal_vbo,Aantal_woningen,Vloeropp_totaal,Vloeropp_bijeenkomst,Vloeropp_gezondheidszorg,Vloeropp_industrie,Vloeropp_kantoor,Vloeropp_onderwijs,Vloeropp_winkel,Vloeropp_woon,Vloeropp_cel,Vloeropp_overig,Vloeropp_logies,Vloeropp_sport,Verh_opp_pand_vloer,SHAPE_Length,SHAPE_Area",VBO_2014,"OBJECTID,Identificatie,Officieel,Oppervlakte,Status,BeginDatum,EindDatum,DocumentDatum,DocumentNummer,AanduidingInOnderzoek,AanduidingRecordCorrectie,AanduidingRecordInactief,HoofdadresID,Gebruiksdoel,opp_totaal,functie_woon,functie_winkel,functie_overig,functie_onderwijs,functie_kantoor,functie_industrie,functie_sport,functie_gezondheidszorg,functie_bijeenkomst,functie_cel,functie_logies,opp_woon,opp_winkel,opp_overig,opp_onderwijs,opp_kantoor,opp_industrie,opp_bijeenkomst,opp_sport,opp_gezondheidszorg,opp_cel,opp_logies,functie_som,Status_bestaand,Gemeente2014,CBS2014,Gemeente,CBScode,functie_werk,functie_voorzieningen",VBO_2021,"OBJECTID,versieidentificatie,Identificatie,Officieel,Oppervlakte,Status,BeginDatum,EindDatum,Documentdatum,Documentnummer,Aanduidinginonderzoek,Hoofdadresid,Gebruiksdoel,Gebruiksdoel1,geometrietype,opp_totaal,functie_woon,functie_winkel,functie_overig,functie_onderwijs,functie_kantoor,functie_industrie,functie_sport,functie_gezondheidszorg,functie_bijeenkomst,functie_cel,functie_logies,functie_voorzieningen,functie_overige,functie_werk,opp_woon,opp_winkel,opp_overig,opp_onderwijs,opp_kantoor,opp_industrie,opp_bijeenkomst,opp_sport,opp_gezondheidszorg,opp_cel,opp_logies,opp_voorzieningen,opp_overige,opp_werk,functie_som,Status_bestaand,huisnummer,huisletter,huisnummertoevoeging,postcode,openbareruimtenaam,woonplaatsnaam,adrestype,typeadresseerbaarobject,adresseerbaarobjectstatus,adresseerbaarobjectgeometrie,adresseerbaarobjectid,openbareruimteid,woonplaatsid,Gemeente,CBScode",VBO_2022,"OBJECTID,EindDatum,BeginDatum,versieidentificatie,Identificatie,voorkomenidentificatie,Oppervlakte,Gebruiksdoel,Gebruiksdoel1,geconstateerd,Status,begingeldigheid,eindgeldigheid,Documentdatum,Documentnummer,tijdstipregistratie,eindregistratie,tijdstipregistratielv,tijdstipeindregistratielv,Hoofdadresid,geometrietype,opp_totaal,functie_woon,functie_winkel,functie_overig,functie_onderwijs,functie_kantoor,functie_industrie,functie_sport,functie_gezondheidszorg,functie_bijeenkomst,functie_cel,functie_logies,functie_voorzieningen,functie_overige,functie_werk,opp_woon,opp_winkel,opp_overig,opp_onderwijs,opp_kantoor,opp_industrie,opp_bijeenkomst,opp_sport,opp_gezondheidszorg,opp_cel,opp_logies,opp_voorzieningen,opp_overige,opp_werk,functie_som,Status_bestaand,huisnummer,huisletter,huisnummertoevoeging,postcode,openbareruimtenaam,woonplaatsnaam,adrestype,typeadresseerbaarobject,adresseerbaarobjectstatus,adresseerbaarobjectgeometrie,adresseerbaarobjectid,openbareruimteid,woonplaatsid,Gemeente,CBScode",VBO_2023,"OBJECTID,EindDatum,BeginDatum,versieidentificatie,Identificatie,voorkomenidentificatie,Oppervlakte,Gebruiksdoel,Gebruiksdoel1,geconstateerd,Status,begingeldigheid,eindgeldigheid,Documentdatum,Documentnummer,tijdstipregistratie,eindregistratie,tijdstipregistratielv,tijdstipeindregistratielv,Hoofdadresid,geometrietype,opp_totaal,functie_woon,functie_winkel,functie_overig,functie_onderwijs,functie_kantoor,functie_industrie,functie_sport,functie_gezondheidszorg,functie_bijeenkomst,functie_cel,functie_logies,functie_voorzieningen,functie_overige,functie_werk,opp_woon,opp_winkel,opp_overig,opp_onderwijs,opp_kantoor,opp_industrie,opp_bijeenkomst,opp_sport,opp_gezondheidszorg,opp_cel,opp_logies,opp_voorzieningen,opp_overige,opp_werk,functie_som,Status_bestaand,huisnummer,huisletter,huisnummertoevoeging,postcode,openbareruimtenaam,woonplaatsnaam,adrestype,typeadresseerbaarobject,adresseerbaarobjectstatus,adresseerbaarobjectgeometrie,adresseerbaarobjectid,openbareruimteid,woonplaatsid,Gemeente,CBScode",VBO_2024,"OBJECTID,EindDatum,BeginDatum,versieidentificatie,Identificatie,voorkomenidentificatie,Oppervlakte,Gebruiksdoel,Gebruiksdoel1,geconstateerd,Status,begingeldigheid,eindgeldigheid,Documentdatum,Documentnummer,tijdstipregistratie,eindregistratie,tijdstipregistratielv,tijdstipeindregistratielv,Hoofdadresid,geometrietype,opp_totaal,functie_woon,functie_winkel,functie_overig,functie_onderwijs,functie_kantoor,functie_industrie,functie_sport,functie_gezondheidszorg,functie_bijeenkomst,functie_cel,functie_logies,functie_voorzieningen,functie_overige,functie_werk,functie_werkenden,opp_woon,opp_winkel,opp_overig,opp_onderwijs,opp_kantoor,opp_industrie,opp_bijeenkomst,opp_sport,opp_gezondheidszorg,opp_cel,opp_logies,opp_voorzieningen,opp_overige,opp_werk,opp_werkenden,functie_som,Status_bestaand,huisnummer,huisletter,huisnummertoevoeging,postcode,openbareruimtenaam,woonplaatsnaam,adrestype,typeadresseerbaarobject,adresseerbaarobjectstatus,adresseerbaarobjectgeometrie,adresseerbaarobjectid,openbareruimteid,woonplaatsid,Gemeente,CBScode"
    ATTR_ACCUM_MODE = Only Use Result
    CLIP_TO_ENVELOPE = YES
    COMBINE_GEOM = Use Result
    DATASET = D:\BAG voorraad.gdb
    FEATURETYPES = VBO_2023
    FORMAT = GEODATABASE_FILE
    GEODATABASE_FILE_ALIAS_MODE = NONE
    GEODATABASE_FILE_CACHE_MULTIPATCH_TEXTURES = yes
    GEODATABASE_FILE_CHECK_SIMPLE_GEOM = no
    GEODATABASE_FILE_CREATE_FEATURE_TABLES_FROM_DATA = Yes
    GEODATABASE_FILE_DISABLE_FEATURE_DATASET_ATTRIBUTE = Yes
    GEODATABASE_FILE_FEATURE_READ_MODE = Features
    GEODATABASE_FILE_IGNORE_NETWORK_INFO = yes
    GEODATABASE_FILE_IGNORE_RELATIONSHIP_INFO = yes
    GEODATABASE_FILE_MERGE_FEAT_LINKED_ANNOS = no
    GEODATABASE_FILE_QUERY_FEATURE_TYPES_FOR_MERGE_FILTERS = Yes
    GEODATABASE_FILE_READ_THREE_POINT_ARCS = no
    GEODATABASE_FILE_REMOVE_FEATURE_DATASET = NO
    GEODATABASE_FILE_RESOLVE_DOMAINS = no
    GEODATABASE_FILE_RESOLVE_SUBTYPE_NAMES = yes
    GEODATABASE_FILE_SIMPLE_DONUT_GEOMETRY = no
    GEODATABASE_FILE_SPLIT_COMPLEX_ANNOS = no
    GEODATABASE_FILE_SPLIT_COMPLEX_EDGES = no
    GEODATABASE_FILE_SPLIT_MULTI_PART_ANNOS = no
    GEODATABASE_FILE_STRIP_GUID_GLOBALID_BRACES = no
    GEODATABASE_FILE_TRANSLATE_SPATIAL_DATA_ONLY = no
    GEODATABASE_FILE_USE_SEARCH_ENVELOPE = NO
    GEOMETRY_TYPES = Pand_2021_adres,"""Shape,fme_area""",Pand_2022_adres,"""SHAPE,fme_area""",Pand_2023_adres,"""Shape,fme_area""",Pand_2024,"""SHAPE,fme_area""",Pand_2024_adres,"""SHAPE,fme_area""",VBO_2014,"""SHAPE,fme_point""",VBO_2021,"""SHAPE,fme_point""",VBO_2022,"""SHAPE,fme_point""",VBO_2023,"""SHAPE,fme_point""",VBO_2024,"""SHAPE,fme_point"""
    INITIATOR_FIRST_OUTPUT = default
    INTERACT = INTERSECTS
    ORDER_RESULTS = No
    OUTPUT_ADD_SCHEMA_ATTRIBUTES = NO
    OUTPUT_FEATURES_DISPLAY = Schema and Data Features

Bookmark: Groenvoorzieiningen
FeatureReader_4 [off]
    ATTRIBUTES = groen_uit_osm_top10_2024,"OBJECTID,type,bron,_area,Shape_Length,Shape_Area"
    ATTR_ACCUM_MODE = Only Use Result
    CLIP_TO_ENVELOPE = NO
    COMBINE_GEOM = Use Result
    DATASET = $(FME_MF_DIR_ENCODED)fme input\Groenvoorzierningen\groenkaart.gdb
    FEATURETYPES = groen_uit_osm_top10_2024
    FORMAT = GEODATABASE_FILE
    GEODATABASE_FILE_ALIAS_MODE = NONE
    GEODATABASE_FILE_CACHE_MULTIPATCH_TEXTURES = yes
    GEODATABASE_FILE_CHECK_SIMPLE_GEOM = no
    GEODATABASE_FILE_CREATE_FEATURE_TABLES_FROM_DATA = Yes
    GEODATABASE_FILE_DISABLE_FEATURE_DATASET_ATTRIBUTE = Yes
    GEODATABASE_FILE_FEATURE_READ_MODE = Features
    GEODATABASE_FILE_IGNORE_NETWORK_INFO = yes
    GEODATABASE_FILE_IGNORE_RELATIONSHIP_INFO = yes
    GEODATABASE_FILE_MERGE_FEAT_LINKED_ANNOS = no
    GEODATABASE_FILE_QUERY_FEATURE_TYPES_FOR_MERGE_FILTERS = Yes
    GEODATABASE_FILE_READ_THREE_POINT_ARCS = no
    GEODATABASE_FILE_REMOVE_FEATURE_DATASET = NO
    GEODATABASE_FILE_RESOLVE_DOMAINS = no
    GEODATABASE_FILE_RESOLVE_SUBTYPE_NAMES = yes
    GEODATABASE_FILE_SIMPLE_DONUT_GEOMETRY = no
    GEODATABASE_FILE_SPLIT_COMPLEX_ANNOS = no
    GEODATABASE_FILE_SPLIT_COMPLEX_EDGES = no
    GEODATABASE_FILE_SPLIT_MULTI_PART_ANNOS = no
    GEODATABASE_FILE_STRIP_GUID_GLOBALID_BRACES = no
    GEODATABASE_FILE_TRANSLATE_SPATIAL_DATA_ONLY = no
    GEODATABASE_FILE_USE_SEARCH_ENVELOPE = NO
    GEOMETRY_TYPES = groen_uit_osm_top10_2024,"""Shape,fme_area"""
    INITIATOR_FIRST_OUTPUT = default
    INTERACT = ENVELOPE_INTERSECTS
    MAX_FEATURES = 500
    ORDER_RESULTS = No
    OUTPUT_ADD_SCHEMA_ATTRIBUTES = NO
    OUTPUT_FEATURES_DISPLAY = Schema and Data Features
    groen_uit_osm_top10_2024 -> TestFilter
