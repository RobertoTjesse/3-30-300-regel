FME workspace 30_2024.fmw

Parameters:
- DestDataset_GEODATABASE_FILE = $(FME_MF_DIR)fme output\30_regel_v2.gdb   # File Geodatabase

Writers:
- GEODATABASE_FILE_1: GEODATABASE_FILE to $(DestDataset_GEODATABASE_FILE)

Bookmark: Iteratie 1
Creator [off]
    GEOMTYPE = Geometry Object
    NUM = 1
    CREATED -> FeatureReader_2 [INITIATOR] [off]
StatisticsCalculator [off]
    ATTR_ACCUM_MODE = All
    CALCULATION_MODE = NUMERIC
    FEAT_STATS = crown_area,NUMERIC_MODE,,,,SUM,,,,,,,,,
    GROUP_BY = wijkcode
    SUMMARY -> FeatureMerger [SUPPLIER] [off]
FeatureMerger [off]
    ATTR_ACCUM_MODE = Merge Supplier
    ATTR_CONFLICT_RES_LOOKUP = REQUESTOR_IF_CONFLICT
    GROUP_BY = wijkcode
    IGNORE_NULLS = No
    JOIN_KEYS = 1 1 AUTO
    MERGE_TYPE = Attributes Only
    PROCESS_DUPS = NO
    REJECT_NULL_MISSING_KEYS = No
    SUPPLIERS_FIRST = No
    ATTR_CONFLICT_RES = Use Requestor
    MERGED -> AttributeManager [off]
AttributeManager [off]
    ATTR_TABLE:
      SET_TO oppervlakte_boom_in_ha (real64) = @Evaluate(@Value(crown_area.sum)/10000)
      SET_TO percentage_groen_land (real64) = @Evaluate(@Value(crown_area.sum)*100/((@Value(oppervlakte_land_in_ha)*10000)))
      REMOVE crown_area (real64)
      REMOVE _related_suppliers (uint32)
      REMOVE crown_area.sum (real64)

Bookmark: PDOK - Wijken, buurten, gemeenten van PZH
FeatureReader_2 [off]
    ATTRIBUTES =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
    ATTR_ACCUM_MODE = Only Use Result
    COMBINE_GEOM = Use Result
    DATASET = $(FME_MF_DIR_ENCODED)fme input\Panden\wijkenbuurten_2023.gpkg
    FEATURETYPES = wijken
    FORMAT = OGCGEOPACKAGE
    GEOMETRY_TYPES = buurten,""",fme_area""",gemeenten,""",fme_area""",wijken,""",fme_area"""
    INTERACT = NONE
    OGCGEOPACKAGE_ENCODE_FEATURE_TYPE_AND_ATTR_NAMES = YES
    OGCGEOPACKAGE_ENFORCE_FOREIGN_KEY_INTEGRITY = YES
    OGCGEOPACKAGE_EXPOSE_PRIMARY_KEY_ATTRIBUTE = YES
    OGCGEOPACKAGE_OPEN_SINGLE_RASTER_AS_SUBDATASET = YES
    OGCGEOPACKAGE_QUERY_FEATURE_TYPES_FOR_MERGE_FILTERS = Yes
    OGCGEOPACKAGE_READER_REPLACE_INVALID_CHARS = NO
    OGCGEOPACKAGE_READ_BOOLEANS_AS_YES_NO = YES
    OGCGEOPACKAGE_READ_NULLS = YES
    OGCGEOPACKAGE_USE_SEARCH_ENVELOPE = NO
    ORDER_RESULTS = No
    OUTPUT_ADD_SCHEMA_ATTRIBUTES = NO
    OUTPUT_FEATURES_DISPLAY = Schema and Data Features
    WHERE = gemeentecode IN ('GM0482','GM0613','GM0484','GM0489','GM1901','GM0502','GM0503','GM0505','GM1924','GM0512','GM0513','GM0518','GM0523','GM0531','GM0534','GM1963','GM1884','GM0537','GM0542','GM1931','GM1621','GM0546','GM0547','GM1916','GM0553','GM0556','GM1842','GM1978','GM0569','GM1930','GM0575','GM0579','GM0590','GM1926','GM0597','GM0603','GM0599','GM0606','GM0610','GM1525','GM0622','GM0626','GM1992','GM0627','GM0629','GM1783','GM0637','GM0638','GM1892','GM0642')
    wijken -> FeatureReader_4 [INITIATOR] [off]
    wijken -> AttributeKeeper [off]
    wijken -> FeatureReader_3 [INITIATOR] [off]
    wijken -> FeatureReader_5 [INITIATOR] [off]

Bookmark: Bomen
FeatureReader_3 [off]
    ATTRIBUTES = BODEM.BOMEN_CENTERPOINTS,"OBJECTID,id,stem_id,tree_id,sys_period,dataset,date,method,quality,accuracy,accuracy_metadata,transaction_id,current_status,status_date",BODEM.BOMEN_KRONEN,"OBJECTID,id,tree_id,valid_period,sys_period,tile_name,current_status,status_date,status_source_id,management_form,management_form_dataset,management_form_date,management_form_method,management_form_quality,crown_area,crown_diameter,crown_dataset,crown_date,crown_method,crown_quality,height,height_dataset,height_date,height_method,height_quality,undergrowth_cover,undergrowth_dataset,undergrowth_date,undergrowth_method,undergrowth_quality,Geo_afgeschermd.BODEM.BOMEN_KRONEN.fid,Shape.STArea(),Shape.STLength()"
    ATTR_ACCUM_MODE = Only Use Result
    COMBINE_GEOM = Use Result
    DATASET = bomen
    FEATURETYPES = BODEM.BOMEN_KRONEN BODEM.BOMEN_CENTERPOINTS
    FORMAT = GEODATABASE_SDE
    GEODATABASE_SDE_ALIAS_MODE = NONE
    GEODATABASE_SDE_CACHE_MULTIPATCH_TEXTURES = yes
    GEODATABASE_SDE_CHECK_SIMPLE_GEOM = no
    GEODATABASE_SDE_CREATE_FEATURE_TABLES_FROM_DATA = Yes
    GEODATABASE_SDE_DISABLE_FEATURE_DATASET_ATTRIBUTE = Yes
    GEODATABASE_SDE_FEATURE_READ_MODE = Features
    GEODATABASE_SDE_IGNORE_NETWORK_INFO = yes
    GEODATABASE_SDE_IGNORE_RELATIONSHIP_INFO = yes
    GEODATABASE_SDE_MERGE_FEAT_LINKED_ANNOS = no
    GEODATABASE_SDE_NAMED_CONNECTION = bomen
    GEODATABASE_SDE_PERSISTENT_CONNECTION = no
    GEODATABASE_SDE_QUERY_FEATURE_TYPES_FOR_MERGE_FILTERS = Yes
    GEODATABASE_SDE_READ_THREE_POINT_ARCS = no
    GEODATABASE_SDE_READ_VERSION_DIFFERENCES = NO
    GEODATABASE_SDE_REMOVE_FEATURE_DATASET = NO
    GEODATABASE_SDE_REMOVE_TABLE_QUALIFIER = NO
    GEODATABASE_SDE_RESOLVE_DOMAINS = no
    GEODATABASE_SDE_RESOLVE_SUBTYPE_NAMES = yes
    GEODATABASE_SDE_SIMPLE_DONUT_GEOMETRY = no
    GEODATABASE_SDE_SPLIT_COMPLEX_ANNOS = no
    GEODATABASE_SDE_SPLIT_COMPLEX_EDGES = no
    GEODATABASE_SDE_SPLIT_MULTI_PART_ANNOS = no
    GEODATABASE_SDE_STRIP_GUID_GLOBALID_BRACES = no
    GEODATABASE_SDE_TRANSLATE_SPATIAL_DATA_ONLY = no
    GEODATABASE_SDE_USE_SEARCH_ENVELOPE = NO
    GEOMETRY_TYPES = BODEM.BOMEN_CENTERPOINTS,""",fme_point""",BODEM.BOMEN_KRONEN,""",fme_area"""
    INTERACT = NONE
    ORDER_RESULTS = No
    OUTPUT_ADD_SCHEMA_ATTRIBUTES = NO
    OUTPUT_FEATURES_DISPLAY = Schema and Data Features
    BODEM.BOMEN_KRONEN -> AttributeKeeper_2 [off]
    BODEM.BOMEN_KRONEN -> FeatureReader_3_BODEM.BOMEN_KRONEN [off]
    BODEM.BOMEN_CENTERPOINTS -> FeatureReader_3_BODEM.BOMEN_CENTERPOINTS [off]

Bookmark: DATA BRONNEN _ Hendrik-Ido-Ambacht JAAR 2023
AttributeKeeper_2 [off]
    CREATE_BULK_MODE_FEATURES = NO
    KEEP_ATTRS = crown_area
    -> SpatialRelator [Requestor] [off]
FeatureReader_3_BODEM.BOMEN_KRONEN: Inspector [off]
FeatureReader_3_BODEM.BOMEN_CENTERPOINTS: Inspector [off]
AttributeKeeper [off]
    CREATE_BULK_MODE_FEATURES = NO
    KEEP_ATTRS = gemeentecode,gemeentenaam,oppervlakte_land_in_ha,oppervlakte_totaal_in_ha,oppervlakte_water_in_ha,wijkcode,wijknaam
    -> Sampler [off]
    -> SpatialRelator [Supplier] [off]
SpatialRelator [off]
    AGGREGATE_HANDLING = Yes
    ATTR_ACCUM_MODE = Merge Supplier
    ATTR_CONFLICT_RES = Use Requestor
    CALC_CARD = No
    CURVE_BOUNDARY_RULE_PARAM = Default Rule
    IGNORE_NULLS = Yes
    PREDICATES = WITHIN
    SUCCESS_ATTR = _related_suppliers
    -> StatisticsCalculator [off]
Sampler [off]
    MODE = ORIGINAL
    RATE = 1
    SAMPLE_TYPE_MULTIPLIER = -1
    SAMPLE_MODE = No
    SAMPLE_TYPE_LONG = First N Features
    SAMPLED -> FeatureMerger [REQUESTOR] [off]
TestFilter [off]
    DEFAULT_VALUE = <UNFILTERED>
    PASSED_TEST_GROUP_OUTPUT = FIRST
    TEST_LIST:
      "BOOL_OP,OR,COMPOSITE_TEST,""""""1 OR 2"""""",TEST_CLAUSE,TEST @Value(type) = meer, plas
      TEST @Value(type) = waterloop",@Value(type) = meer, plas

Bookmark: Panden Verblijfobjecten
FeatureReader_4 [off]
    ATTRIBUTES = Pand_2021_adres,"OBJECTID,Adres,bouwperiode,CBScode,Gemeente,identificatie,bouwjaar,officieel,status,begindatum,einddatum,documentdatum,documentnummer,aanduidinginonderzoek,aanduidingrecordcorrectie,aanduidingrecordinactief,Status_bestaand,Pand_oppervlakte,pandid,huisnummer,postcode,openbareruimtenaam,woonplaatsnaam,Aantal_vbo,Vloeropp_totaal,Vloeropp_bijeenkomst,Vloeropp_gezondheidszorg,Vloeropp_industrie,Vloeropp_kantoor,Vloeropp_onderwijs,Vloeropp_voorzieningen,Vloeropp_werk,Vloeropp_winkel,Vloeropp_woon,Verh_opp_pand_vloer,Shape_Length,Shape_Area",Pand_2022_adres,"OBJECTID,identificatie,Adres,openbareruimtenaam,huisnummer_start,huisnummer_eind,postcode,woonplaatsnaam,Gemeente,CBScode,Aantal_vbo,begindatum,einddatum,bouwjaar,bouwperiode,status,Status_bestaand,Pand_oppervlakte,Vloeropp_totaal,Vloeropp_bijeenkomst,Vloeropp_gezondheidszorg,Vloeropp_industrie,Vloeropp_kantoor,Vloeropp_onderwijs,Vloeropp_winkel,Vloeropp_woon,Vloeropp_cel,Vloeropp_overig,Vloeropp_logies,Vloeropp_sport,Verh_opp_pand_vloer,SHAPE_Length,SHAPE_Area",Pand_2023_adres,"OBJECTID,Adres,huisnummer_start,huisnummer_eind,bouwperiode,CBScode,Gemeente,einddatum,begindatum,identificatie,bouwjaar,status,Pand_oppervlakte,postcode,openbareruimtenaam,woonplaatsnaam,Aantal_vbo,Aantal_woningen,Vloeropp_totaal,Vloeropp_bijeenkomst,Vloeropp_gezondheidszorg,Vloeropp_industrie,Vloeropp_kantoor,Vloeropp_onderwijs,Vloeropp_winkel,Vloeropp_woon,Vloeropp_cel,Vloeropp_overig,Vloeropp_logies,Vloeropp_sport,Verh_opp_pand_vloer,Status_bestaand,Shape_Length,Shape_Area",Pand_2024,"OBJECTID,CBScode,Gemeente,jaar_einde,einddatum,begindatum,identificatie,voorkomenidentificatie,bouwjaar,geconstateerd,status,begingeldigheid,eindgeldigheid,documentdatum,documentnummer,tijdstipregistratie,eindregistratie,tijdstipregistratielv,tijdstipeindregistratielv,Status_bestaand,SHAPE_Length,SHAPE_Area",Pand_2024_adres,"OBJECTID,Adres,huisnummer_start,huisnummer_eind,bouwperiode,CBScode,Gemeente,einddatum,begindatum,identificatie,voorkomenidentificatie,bouwjaar,geconstateerd,status,begingeldigheid,eindgeldigheid,documentdatum,documentnummer,tijdstipregistratie,eindregistratie,tijdstipregistratielv,tijdstipeindregistratielv,Pand_oppervlakte,postcode,openbareruimtenaam,woonplaatsnaam,Aantal_vbo,Aantal_woningen,Vloeropp_totaal,Vloeropp_bijeenkomst,Vloeropp_gezondheidszorg,Vloeropp_industrie,Vloeropp_kantoor,Vloeropp_onderwijs,Vloeropp_winkel,Vloeropp_woon,Vloeropp_cel,Vloeropp_overig,Vloeropp_logies,Vloeropp_sport,Verh_opp_pand_vloer,SHAPE_Length,SHAPE_Area",VBO_2014,"OBJECTID,Identificatie,Officieel,Oppervlakte,Status,BeginDatum,EindDatum,DocumentDatum,DocumentNummer,AanduidingInOnderzoek,AanduidingRecordCorrectie,AanduidingRecordInactief,HoofdadresID,Gebruiksdoel,opp_totaal,functie_woon,functie_winkel,functie_overig,functie_onderwijs,functie_kantoor,functie_industrie,functie_sport,functie_gezondheidszorg,functie_bijeenkomst,functie_cel,functie_logies,opp_woon,opp_winkel,opp_overig,opp_onderwijs,opp_kantoor,opp_industrie,opp_bijeenkomst,opp_sport,opp_gezondheidszorg,opp_cel,opp_logies,functie_som,Status_bestaand,Gemeente2014,CBS2014,Gemeente,CBScode,functie_werk,functie_voorzieningen",VBO_2021,"OBJECTID,versieidentificatie,Identificatie,Officieel,Oppervlakte,Status,BeginDatum,EindDatum,Documentdatum,Documentnummer,Aanduidinginonderzoek,Hoofdadresid,Gebruiksdoel,Gebruiksdoel1,geometrietype,opp_totaal,functie_woon,functie_winkel,functie_overig,functie_onderwijs,functie_kantoor,functie_industrie,functie_sport,functie_gezondheidszorg,functie_bijeenkomst,functie_cel,functie_logies,functie_voorzieningen,functie_overige,functie_werk,opp_woon,opp_winkel,opp_overig,opp_onderwijs,opp_kantoor,opp_industrie,opp_bijeenkomst,opp_sport,opp_gezondheidszorg,opp_cel,opp_logies,opp_voorzieningen,opp_overige,opp_werk,functie_som,Status_bestaand,huisnummer,huisletter,huisnummertoevoeging,postcode,openbareruimtenaam,woonplaatsnaam,adrestype,typeadresseerbaarobject,adresseerbaarobjectstatus,adresseerbaarobjectgeometrie,adresseerbaarobjectid,openbareruimteid,woonplaatsid,Gemeente,CBScode",VBO_2022,"OBJECTID,EindDatum,BeginDatum,versieidentificatie,Identificatie,voorkomenidentificatie,Oppervlakte,Gebruiksdoel,Gebruiksdoel1,geconstateerd,Status,begingeldigheid,eindgeldigheid,Documentdatum,Documentnummer,tijdstipregistratie,eindregistratie,tijdstipregistratielv,tijdstipeindregistratielv,Hoofdadresid,geometrietype,opp_totaal,functie_woon,functie_winkel,functie_overig,functie_onderwijs,functie_kantoor,functie_industrie,functie_sport,functie_gezondheidszorg,functie_bijeenkomst,functie_cel,functie_logies,functie_voorzieningen,functie_overige,functie_werk,opp_woon,opp_winkel,opp_overig,opp_onderwijs,opp_kantoor,opp_industrie,opp_bijeenkomst,opp_sport,opp_gezondheidszorg,opp_cel,opp_logies,opp_voorzieningen,opp_overige,opp_werk,functie_som,Status_bestaand,huisnummer,huisletter,huisnummertoevoeging,postcode,openbareruimtenaam,woonplaatsnaam,adrestype,typeadresseerbaarobject,adresseerbaarobjectstatus,adresseerbaarobjectgeometrie,adresseerbaarobjectid,openbareruimteid,woonplaatsid,Gemeente,CBScode",VBO_2023,"OBJECTID,EindDatum,BeginDatum,versieidentificatie,Identificatie,voorkomenidentificatie,Oppervlakte,Gebruiksdoel,Gebruiksdoel1,geconstateerd,Status,begingeldigheid,eindgeldigheid,Documentdatum,Documentnummer,tijdstipregistratie,eindregistratie,tijdstipregistratielv,tijdstipeindregistratielv,Hoofdadresid,geometrietype,opp_totaal,functie_woon,functie_winkel,functie_overig,functie_onderwijs,functie_kantoor,functie_industrie,functie_sport,functie_gezondheidszorg,functie_bijeenkomst,functie_cel,functie_logies,functie_voorzieningen,functie_overige,functie_werk,opp_woon,opp_winkel,opp_overig,opp_onderwijs,opp_kantoor,opp_industrie,opp_bijeenkomst,opp_sport,opp_gezondheidszorg,opp_cel,opp_logies,opp_voorzieningen,opp_overige,opp_werk,functie_som,Status_bestaand,huisnummer,huisletter,huisnummertoevoeging,postcode,openbareruimtenaam,woonplaatsnaam,adrestype,typeadresseerbaarobject,adresseerbaarobjectstatus,adresseerbaarobjectgeometrie,adresseerbaarobjectid,openbareruimteid,woonplaatsid,Gemeente,CBScode",VBO_2024,"OBJECTID,EindDatum,BeginDatum,versieidentificatie,Identificatie,voorkomenidentificatie,Oppervlakte,Gebruiksdoel,Gebruiksdoel1,geconstateerd,Status,begingeldigheid,eindgeldigheid,Documentdatum,Documentnummer,tijdstipregistratie,eindregistratie,tijdstipregistratielv,tijdstipeindregistratielv,Hoofdadresid,geometrietype,opp_totaal,functie_woon,functie_winkel,functie_overig,functie_onderwijs,functie_kantoor,functie_industrie,functie_sport,functie_gezondheidszorg,functie_bijeenkomst,functie_cel,functie_logies,functie_voorzieningen,functie_overige,functie_werk,functie_werkenden,opp_woon,opp_winkel,opp_overig,opp_onderwijs,opp_kantoor,opp_industrie,opp_bijeenkomst,opp_sport,opp_gezondheidszorg,opp_cel,opp_logies,opp_voorzieningen,opp_overige,opp_werk,opp_werkenden,functie_som,Status_bestaand,huisnummer,huisletter,huisnummertoevoeging,postcode,openbareruimtenaam,woonplaatsnaam,adrestype,typeadresseerbaarobject,adresseerbaarobjectstatus,adresseerbaarobjectgeometrie,adresseerbaarobjectid,openbareruimteid,woonplaatsid,Gemeente,CBScode"
    ATTR_ACCUM_MODE = Only Use Result
    COMBINE_GEOM = Use Result
    DATASET = D:\BAG voorraad.gdb
    FEATURETYPES = VBO_2023
    FORMAT = GEODATABASE_FILE
    GEODATABASE_FILE_ALIAS_MODE = NONE
    GEODATABASE_FILE_CACHE_MULTIPATCH_TEXTURES = yes
    GEODATABASE_FILE_CHECK_SIMPLE_GEOM = no
    GEODATABASE_FILE_CREATE_FEATURE_TABLES_FROM_DATA = Yes
    GEODATABASE_FILE_DISABLE_FEATURE_DATASET_ATTRIBUTE = Yes
    GEODATABASE_FILE_FEATURE_READ_MODE = Features
    GEODATABASE_FILE_IGNORE_NETWORK_INFO = yes
    GEODATABASE_FILE_IGNORE_RELATIONSHIP_INFO = yes
    GEODATABASE_FILE_MERGE_FEAT_LINKED_ANNOS = no
    GEODATABASE_FILE_QUERY_FEATURE_TYPES_FOR_MERGE_FILTERS = Yes
    GEODATABASE_FILE_READ_THREE_POINT_ARCS = no
    GEODATABASE_FILE_REMOVE_FEATURE_DATASET = NO
    GEODATABASE_FILE_RESOLVE_DOMAINS = no
    GEODATABASE_FILE_RESOLVE_SUBTYPE_NAMES = yes
    GEODATABASE_FILE_SIMPLE_DONUT_GEOMETRY = no
    GEODATABASE_FILE_SPLIT_COMPLEX_ANNOS = no
    GEODATABASE_FILE_SPLIT_COMPLEX_EDGES = no
    GEODATABASE_FILE_SPLIT_MULTI_PART_ANNOS = no
    GEODATABASE_FILE_STRIP_GUID_GLOBALID_BRACES = no
    GEODATABASE_FILE_TRANSLATE_SPATIAL_DATA_ONLY = no
    GEODATABASE_FILE_USE_SEARCH_ENVELOPE = NO
    GEOMETRY_TYPES = Pand_2021_adres,""",fme_area""",Pand_2022_adres,""",fme_area""",Pand_2023_adres,""",fme_area""",Pand_2024,""",fme_area""",Pand_2024_adres,""",fme_area""",VBO_2014,""",fme_point""",VBO_2021,""",fme_point""",VBO_2022,""",fme_point""",VBO_2023,""",fme_point""",VBO_2024,""",fme_point"""
    INTERACT = INTERSECTS
    ORDER_RESULTS = No
    OUTPUT_ADD_SCHEMA_ATTRIBUTES = NO
    OUTPUT_FEATURES_DISPLAY = Schema and Data Features

Bookmark: Groenvoorzieiningen
FeatureReader_5 [off]
    ATTRIBUTES = groen_uit_osm_top10_2024,"OBJECTID,type,bron,_area,Shape_Length,Shape_Area"
    ATTR_ACCUM_MODE = Only Use Result
    COMBINE_GEOM = Use Result
    DATASET = $(FME_MF_DIR_ENCODED)fme input\Groenvoorzierningen\groenkaart.gdb
    FEATURETYPES = groen_uit_osm_top10_2024
    FORMAT = GEODATABASE_FILE
    GEODATABASE_FILE_ALIAS_MODE = NONE
    GEODATABASE_FILE_CACHE_MULTIPATCH_TEXTURES = yes
    GEODATABASE_FILE_CHECK_SIMPLE_GEOM = no
    GEODATABASE_FILE_CREATE_FEATURE_TABLES_FROM_DATA = Yes
    GEODATABASE_FILE_DISABLE_FEATURE_DATASET_ATTRIBUTE = Yes
    GEODATABASE_FILE_FEATURE_READ_MODE = Features
    GEODATABASE_FILE_IGNORE_NETWORK_INFO = yes
    GEODATABASE_FILE_IGNORE_RELATIONSHIP_INFO = yes
    GEODATABASE_FILE_MERGE_FEAT_LINKED_ANNOS = no
    GEODATABASE_FILE_QUERY_FEATURE_TYPES_FOR_MERGE_FILTERS = Yes
    GEODATABASE_FILE_READ_THREE_POINT_ARCS = no
    GEODATABASE_FILE_REMOVE_FEATURE_DATASET = NO
    GEODATABASE_FILE_RESOLVE_DOMAINS = no
    GEODATABASE_FILE_RESOLVE_SUBTYPE_NAMES = yes
    GEODATABASE_FILE_SIMPLE_DONUT_GEOMETRY = no
    GEODATABASE_FILE_SPLIT_COMPLEX_ANNOS = no
    GEODATABASE_FILE_SPLIT_COMPLEX_EDGES = no
    GEODATABASE_FILE_SPLIT_MULTI_PART_ANNOS = no
    GEODATABASE_FILE_STRIP_GUID_GLOBALID_BRACES = no
    GEODATABASE_FILE_TRANSLATE_SPATIAL_DATA_ONLY = no
    GEODATABASE_FILE_USE_SEARCH_ENVELOPE = NO
    GEOMETRY_TYPES = groen_uit_osm_top10_2024,""",fme_area"""
    INTERACT = ENVELOPE_INTERSECTS
    MAX_FEATURES = 500
    ORDER_RESULTS = No
    OUTPUT_ADD_SCHEMA_ATTRIBUTES = NO
    OUTPUT_FEATURES_DISPLAY = Schema and Data Features
    groen_uit_osm_top10_2024 -> TestFilter [off]

Bookmark: Iteratie 2 - wijken
Creator_2
    GEOMTYPE = Geometry Object
    NUM = 1
    CREATED -> FeatureReader_6 [INITIATOR]
FeatureReader_6
    ATTRIBUTES =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
    ATTR_ACCUM_MODE = Only Use Result
    COMBINE_GEOM = Use Result
    DATASET = $(FME_MF_DIR_ENCODED)fme input\Panden\wijkenbuurten_2023.gpkg
    FEATURETYPES = wijken
    FORMAT = OGCGEOPACKAGE
    GEOMETRY_TYPES = buurten,""",fme_area""",gemeenten,""",fme_area""",wijken,""",fme_area"""
    INTERACT = NONE
    OGCGEOPACKAGE_ENCODE_FEATURE_TYPE_AND_ATTR_NAMES = YES
    OGCGEOPACKAGE_ENFORCE_FOREIGN_KEY_INTEGRITY = YES
    OGCGEOPACKAGE_EXPOSE_PRIMARY_KEY_ATTRIBUTE = YES
    OGCGEOPACKAGE_OPEN_SINGLE_RASTER_AS_SUBDATASET = YES
    OGCGEOPACKAGE_QUERY_FEATURE_TYPES_FOR_MERGE_FILTERS = Yes
    OGCGEOPACKAGE_READER_REPLACE_INVALID_CHARS = NO
    OGCGEOPACKAGE_READ_BOOLEANS_AS_YES_NO = YES
    OGCGEOPACKAGE_READ_NULLS = YES
    OGCGEOPACKAGE_USE_SEARCH_ENVELOPE = NO
    ORDER_RESULTS = No
    OUTPUT_ADD_SCHEMA_ATTRIBUTES = NO
    OUTPUT_FEATURES_DISPLAY = Schema and Data Features
    WHERE = gemeentecode IN ('GM0482','GM0613','GM0484','GM0489','GM1901','GM0502','GM0503','GM0505','GM1924','GM0512','GM0513','GM0518','GM0523','GM0531','GM0534','GM1963','GM1884','GM0537','GM0542','GM1931','GM1621','GM0546','GM0547','GM1916','GM0553','GM0556','GM1842','GM1978','GM0569','GM1930','GM0575','GM0579','GM0590','GM1926','GM0597','GM0603','GM0599','GM0606','GM0610','GM1525','GM0622','GM0626','GM1992','GM0627','GM0629','GM1783','GM0637','GM0638','GM1892','GM0642')
    wijken -> SQLExecutor [INITIATOR]
    wijken -> FeatureJoiner [LEFT]
SQLExecutor
    COMBINE_ATTRS = Result Attributes Only
    COMBINE_GEOM = Result Geometry Only
    DATASET = sql_geo
    FORMAT = MSSQL_SPATIAL
    MSSQL_SPATIAL_APPLICATION_INTENT = ReadWrite
    MSSQL_SPATIAL_COMMAND_TIMEOUT = 200
    MSSQL_SPATIAL_CREATE_FEATURE_TABLES_FROM_DATA = Yes
    MSSQL_SPATIAL_NAMED_CONNECTION = sql_geo
    MSSQL_SPATIAL_QUERY_FEATURE_TYPES_FOR_MERGE_FILTERS = Yes
    OUTPUT_FEATURES = DATA_ONLY
    SQL_STATEMENT:
      WITH wijk_geom AS (
        SELECT
          wijkcode,
          SHAPE AS wijk_shape
        FROM GRENZEN.CBS_WIJKKAART_2022_VERSIE3
        WHERE wijkcode = '@Value(wijkcode)'
      ),

      bomen_in_wijk AS (
        SELECT
          b.CROWN_AREA
        FROM BODEM.BOMEN_KRONEN b
        JOIN wijk_geom w
          ON b.SHAPE.STIntersects(w.wijk_shape) = 1
      )

      SELECT
        '@Value(wijkcode)' AS wijkcode,
        SUM(CROWN_AREA) AS totaal_kroonoppervlak_m2
      FROM bomen_in_wijk;
    RESULT -> AttributeExposer
    <REJECTED> -> Logger
AttributeExposer
    ATTR_TABLE = wijkcode,,totaal_kroonoppervlak_m2,
    -> FeatureJoiner [RIGHT]
FeatureJoiner
    ATTR_CONFLICT_RES_LOOKUP = USE_LEFT
    GEOMETRY_HANDLING_LOOKUP = USE_LEFT
    JOIN_KEYS = wijkcode wijkcode AUTO
    JOIN_MODE = Inner
    ATTR_CONFLICT_RES = Prefer Left
    GEOMETRY_HANDLING = Prefer Left
    JOINED -> AttributeManager_2
AttributeManager_2
    ATTR_TABLE:
      SET_TO Percentage groen (real64) = @Evaluate((@Value(totaal_kroonoppervlak_m2)/100)/@Value(oppervlakte_land_in_ha))
      SET_TO
    -> FeatureClass1 (writer GEODATABASE_FILE_1)
FeatureClass1 (writer GEODATABASE_FILE_1)
    attributes: wijkcode char(2048), wijknaam char(2048), gemeentecode char(2048), gemeentenaam char(2048), indelingswijziging_wijken_en_buurten integer, water char(2048), omgevingsadressendichtheid integer, stedelijkheid_adressen_per_km2 integer, bevolkingsdichtheid_inwoners_per_km2 integer, aantal_inwoners integer, mannen integer, vrouwen integer, percentage_personen_0_tot_15_jaar integer, percentage_personen_15_tot_25_jaar integer, percentage_personen_25_tot_45_jaar integer, percentage_personen_45_tot_65_jaar integer, percentage_personen_65_jaar_en_ouder integer, percentage_ongehuwd integer, percentage_gehuwd integer, percentage_gescheid integer, percentage_verweduwd integer, geboorte_totaal integer, geboortes_per_1000_inwoners integer, sterfte_totaal integer, sterfte_relatief integer, aantal_huishoudens integer, percentage_eenpersoonshuishoudens integer, percentage_huishoudens_zonder_kinderen integer, percentage_huishoudens_met_kinderen integer, gemiddelde_huishoudsgrootte double,
      percentage_met_herkomstland_nederland integer, percentage_met_herkomstland_uit_europa_excl_nl integer, percentage_met_herkomstland_buiten_europa integer, percentage_geb_in_nl_met_herkomstland_nederland integer, perc_geb_in_nl_met_herkomstland_in_europa_ex_nl integer, perc_geb_in_nl_met_herkomstland_buiten_europa integer, perc_geb_buiten_nl_met_herkomstlnd_in_europa_ex_nl integer, perc_geb_buiten_nl_met_herkomstlnd_buiten_europa integer, aantal_bedrijven_landbouw_bosbouw_visserij integer, aantal_bedrijven_nijverheid_energie integer, aantal_bedrijven_handel_en_horeca integer, aantal_bedrijven_vervoer_informatie_communicatie integer, aantal_bedrijven_financieel_onroerend_goed integer, aantal_bedrijven_zakelijke_dienstverlening integer, aantal_bedrijven_overheid_onderwijs_en_zorg integer, aantal_bedrijven_cultuur_recreatie_overige integer, aantal_bedrijfsvestigingen integer, woningvoorraad integer, gemiddelde_woningwaarde integer, percentage_eengezinswoning integer, percentage_meergezinswoning integer, percentage_bewoond integer, percentage_koopwoningen integer, percentage_huurwoningen integer, perc_huurwoningen_in_bezit_woningcorporaties integer, perc_huurwoningen_in_bezit_overige_verhuurders integer, percentage_woningen_met_eigendom_onbekend integer, percentage_bouwjaarklasse_tot_2000 integer, percentage_bouwjaarklasse_vanaf_2000 integer, percentage_leegstand_woningen integer,
      gemiddeld_gasverbruik_totaal integer, gemiddeld_gasverbruik_appartement integer, gemiddeld_gasverbruik_tussenwoning integer, gemiddeld_gasverbruik_hoekwoning integer, gemiddeld_gasverbruik_2_onder_1_kap_woning integer, gemiddeld_gasverbruik_vrijstaande_woning integer, gemiddeld_gasverbruik_huurwoning integer, gemiddeld_gasverbruikkoopwoning integer, gemiddeld_elektriciteitsverbruik_totaal integer, gemiddeld_elektriciteitsverbruik_appartement integer, gemiddeld_elektriciteitsverbruik_tussenwoning integer, gemiddeld_elektriciteitsverbruik_hoekwoning integer, gem_elektriciteitsverbruik_2_onder_1_kap_woning integer, gem_elektriciteitsverbruik_vrijstaande_woning integer, gemiddeld_elektriciteitsverbruik_huurwoning integer, gemiddeld_elektriciteitsverbruikkoopwoning integer, percentage_woningen_met_stadsverwarming integer, opleidingsniveau_laag integer, opleidingsniveau_middelbaar integer, opleidingsniveau_hoog integer, netto_arbeidsparticipatie integer, percentage_werknemers integer, percentage_zelfstandigen integer, aantal_inkomensontvangers integer, gemiddeld_inkomen_per_inkomensontvanger integer, gemiddeld_inkomen_per_inwoner integer, percentage_personen_met_hoog_inkomen integer, percentage_personen_met_laag_inkomen integer, percentage_huishoudens_met_hoog_inkomen integer, percentage_huishoudens_met_laag_inkomen integer,
      percentage_huishoudens_met_laagste_inkomen integer, percentage_huishoudens_onder_of_rond_sociaal_minimum integer, aantal_personen_met_een_ao_uitkering_totaal integer, aantal_personen_met_een_ww_uitkering_totaal integer, aantal_personen_met_een_alg_bijstandsuitkering_tot integer, aantal_personen_met_een_aow_uitkering_totaal integer, gemiddeld_gestandaardiseerd_inkomen_van_huishoudens double, huishoudens_tot_110_percent_van_sociaal_minimum double, huishoudens_tot_120_percent_van_sociaal_minimum double, mediaan_vermogen_van_particuliere_huish double, aantal_jongeren_met_jeugdzorg_in_natura integer, percentage_jongeren_met_jeugdzorg_in_natura double, aantal_wmo_clienten integer, aantal_wmo_clienten_per_1000_inwoners integer, personenautos_totaal integer, personenautos_per_huishouden double, personenautos_per_km2 integer, motortweewielers_totaal integer, aantal_personenautos_met_brandstof_benzine integer, aantal_personenautos_met_overige_brandstof integer, oppervlakte_totaal_in_ha integer, oppervlakte_land_in_ha integer, oppervlakte_water_in_ha integer, huisartsenpraktijk_gemiddelde_afstand_in_km double, huisartsenpraktijk_gemiddeld_aantal_binnen_1_km double, huisartsenpraktijk_gemiddeld_aantal_binnen_3_km double, huisartsenpraktijk_gemiddeld_aantal_binnen_5_km double, huisartsenpost_gemiddelde_afstand_in_km double, apotheek_gemiddelde_afstand_in_km double, ziekenhuis_incl_buitenpolikliniek_gem_afst_in_km double,
      ziekenhuis_incl_buitenpoli_gem_aantal_binnen_5_km double, ziekenhuis_incl_buitenpoli_gem_aantal_binnen_10_km double, ziekenhuis_incl_buitenpoli_gem_aantal_binnen_20_km double, ziekenhuis_excl_buitenpolikliniek_gem_afst_in_km double, ziekenhuis_excl_buitenpoli_gem_aantal_binnen_5_km double, ziekenhuis_excl_buitenpoli_gem_aantal_binnen_10_km double, ziekenhuis_excl_buitenpoli_gem_aantal_binnen_20_km double, grote_supermarkt_gemiddelde_afstand_in_km double, grote_supermarkt_gemiddeld_aantal_binnen_1_km double, grote_supermarkt_gemiddeld_aantal_binnen_3_km double, grote_supermarkt_gemiddeld_aantal_binnen_5_km double, winkels_ov_dagelijkse_levensm_gem_afst_in_km double, winkels_ov_dagel_levensm_gem_aantal_binnen_1_km double, winkels_ov_dagel_levensm_gem_aantal_binnen_3_km double, winkels_ov_dagel_levensm_gem_aantal_binnen_5_km double, warenhuis_gemiddelde_afstand_in_km double, warenhuis_gemiddeld_aantal_binnen_5_km double, warenhuis_gemiddeld_aantal_binnen_10_km double, warenhuis_gemiddeld_aantal_binnen_20_km double, cafe_gemiddelde_afstand_in_km double, cafe_gemiddeld_aantal_binnen_1_km double, cafe_gemiddeld_aantal_binnen_3_km double, cafe_gemiddeld_aantal_binnen_5_km double, cafetaria_gemiddelde_afstand_in_km double, cafetaria_gemiddeld_aantal_binnen_1_km double, cafetaria_gemiddeld_aantal_binnen_3_km double, cafetaria_gemiddeld_aantal_binnen_5_km double, restaurant_gemiddelde_afstand_in_km double, restaurant_gemiddeld_aantal_binnen_1_km double, restaurant_gemiddeld_aantal_binnen_3_km double,
      restaurant_gemiddeld_aantal_binnen_5_km double, hotel_gemiddelde_afstand_in_km double, hotel_gemiddeld_aantal_binnen_5_km double, hotel_gemiddeld_aantal_binnen_10_km double, hotel_gemiddeld_aantal_binnen_20_km double, kinderdagverblijf_gemiddelde_afstand_in_km double, kinderdagverblijf_gemiddeld_aantal_binnen_1_km double, kinderdagverblijf_gemiddeld_aantal_binnen_3_km double, kinderdagverblijf_gemiddeld_aantal_binnen_5_km double, buitenschoolse_opvang_gem_afstand_in_km double, buitenschoolse_opvang_gemiddeld_aantal_binnen_1_km double, buitenschoolse_opvang_gemiddeld_aantal_binnen_3_km double, buitenschoolse_opvang_gemiddeld_aantal_binnen_5_km double, basisonderwijs_gemiddelde_afstand_in_km double, basisonderwijs_gemiddeld_aantal_binnen_1_km double, basisonderwijs_gemiddeld_aantal_binnen_3_km double, basisonderwijs_gemiddeld_aantal_binnen_5_km double, voortgezet_onderwijs_gem_afstand_in_km double, voortgezet_onderwijs_gemiddeld_aantal_binnen_3_km double, voortgezet_onderwijs_gemiddeld_aantal_binnen_5_km double, voortgezet_onderwijs_gemiddeld_aantal_binnen_10_km double, vmbo_gemiddelde_afstand_in_km double, vmbo_gemiddeld_aantal_binnen_3_km double, vmbo_gemiddeld_aantal_binnen_5_km double, vmbo_gemiddeld_aantal_binnen_10_km double, havo_vwo_gemiddelde_afstand_in_km double, havo_vwo_gemiddeld_aantal_binnen_3_km double, havo_vwo_gemiddeld_aantal_binnen_5_km double, havo_vwo_gemiddeld_aantal_binnen_10_km double, brandweerkazerne_gemiddelde_afstand_in_km double,
      oprit_hoofdverkeersweg_gemiddelde_afstand_in_km double, treinstation_gemiddelde_afstand_in_km double, overstapstation_gemiddelde_afstand_in_km double, zwembad_gemiddelde_afstand_in_km double, kunstijsbaan_gemiddelde_afstand_in_km double, bibliotheek_gemiddelde_afstand_in_km double, poppodium_gemiddelde_afstand_in_km double, bioscoop_gemiddelde_afstand_in_km double, bioscoop_gemiddeld_aantal_binnen_5_km double, bioscoop_gemiddeld_aantal_binnen_10_km double, bioscoop_gemiddeld_aantal_binnen_20_km double, sauna_gemiddelde_afstand_in_km double, zonnebank_gemiddelde_afstand_in_km double, attractiepark_gemiddelde_afstand_in_km double, attractiepark_gemiddeld_aantal_binnen_10_km double, attractiepark_gemiddeld_aantal_binnen_20_km double, attractiepark_gemiddeld_aantal_binnen_50_km double, theater_gemiddelde_afstand_in_km double, theater_gemiddeld_aantal_binnen_5_km double, theater_gemiddeld_aantal_binnen_10_km double, theater_gemiddeld_aantal_binnen_20_km double, gemiddelde_afstand_tot_museum double, gemiddeld_aantal_musea_binnen_5_km double, gemiddeld_aantal_musea_binnen_10_km double, gemiddeld_aantal_musea_binnen_20_km double, afstand_tot_openbaar_groen_totaal double, afstand_tot_park_of_plantsoen double, afstand_tot_dagrcreatief_terrein double, afstand_tot_bos double, afstand_tot_open_natuur_terrein_totaal double,
      afstand_tot_open_droog_natuur_terrein double, afstand_tot_open_nat_natuurlijk_terrein double, afstand_tot_semiopenbaar_groen_totaal double, afstand_tot_sportterrein double, afstand_tot_volkstuin double, afstand_tot_verblijfsrecreatief_terrein double, afstand_tot_recreatief_binnenwater double, afstand_tot_begraafplaats double, jrstatcode char(2048), jaar integer, fid bigint, totaal_kroonoppervlak_m2 char(200), Percentage_groen double
Logger
    LOG_FEATURE = LOG_ONLY
    MAXCOORDS = 20
    MAXFEATS = 20
    MESSAGE = Feature is:
    SEVERITY = INFO

Bookmark: Iteratie 2 - buurten
Creator_3
    GEOMTYPE = Geometry Object
    NUM = 1
    CREATED -> FeatureReader_7 [INITIATOR]
FeatureReader_7
    ATTRIBUTES =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
    ATTR_ACCUM_MODE = Only Use Result
    COMBINE_GEOM = Use Result
    DATASET = $(FME_MF_DIR_ENCODED)fme input\Panden\wijkenbuurten_2023.gpkg
    FEATURETYPES = buurten
    FORMAT = OGCGEOPACKAGE
    GEOMETRY_TYPES = buurten,"""geom,fme_area""",gemeenten,"""geom,fme_area""",wijken,"""geom,fme_area"""
    INTERACT = NONE
    OGCGEOPACKAGE_ENCODE_FEATURE_TYPE_AND_ATTR_NAMES = YES
    OGCGEOPACKAGE_ENFORCE_FOREIGN_KEY_INTEGRITY = YES
    OGCGEOPACKAGE_EXPOSE_PRIMARY_KEY_ATTRIBUTE = YES
    OGCGEOPACKAGE_OPEN_SINGLE_RASTER_AS_SUBDATASET = YES
    OGCGEOPACKAGE_QUERY_FEATURE_TYPES_FOR_MERGE_FILTERS = Yes
    OGCGEOPACKAGE_READER_REPLACE_INVALID_CHARS = NO
    OGCGEOPACKAGE_READ_BOOLEANS_AS_YES_NO = YES
    OGCGEOPACKAGE_READ_NULLS = YES
    OGCGEOPACKAGE_USE_SEARCH_ENVELOPE = NO
    ORDER_RESULTS = No
    OUTPUT_ADD_SCHEMA_ATTRIBUTES = NO
    OUTPUT_FEATURES_DISPLAY = Schema and Data Features
    WHERE = gemeentecode IN ('GM0482','GM0613','GM0484','GM0489','GM1901','GM0502','GM0503','GM0505','GM1924','GM0512','GM0513','GM0518','GM0523','GM0531','GM0534','GM1963','GM1884','GM0537','GM0542','GM1931','GM1621','GM0546','GM0547','GM1916','GM0553','GM0556','GM1842','GM1978','GM0569','GM1930','GM0575','GM0579','GM0590','GM1926','GM0597','GM0603','GM0599','GM0606','GM0610','GM1525','GM0622','GM0626','GM1992','GM0627','GM0629','GM1783','GM0637','GM0638','GM1892','GM0642')
    buurten -> AttributeKeeper_3
    buurten -> FeatureJoiner_2 [LEFT]
AttributeKeeper_3
    CREATE_BULK_MODE_FEATURES = NO
    KEEP_ATTRS = buurtcode
    -> SQLExecutor_2 [INITIATOR]
SQLExecutor_2
    COMBINE_ATTRS = Result Attributes Only
    COMBINE_GEOM = Result Geometry Only
    DATASET = sql_geo
    FORMAT = MSSQL_SPATIAL
    MSSQL_SPATIAL_APPLICATION_INTENT = ReadWrite
    MSSQL_SPATIAL_COMMAND_TIMEOUT = 200
    MSSQL_SPATIAL_CREATE_FEATURE_TABLES_FROM_DATA = Yes
    MSSQL_SPATIAL_NAMED_CONNECTION = sql_geo
    MSSQL_SPATIAL_QUERY_FEATURE_TYPES_FOR_MERGE_FILTERS = Yes
    OUTPUT_FEATURES = DATA_ONLY
    SQL_STATEMENT:
      WITH buurt_geom AS (
        SELECT
          buurtcode,
          SHAPE AS buurt_shape
        FROM GRENZEN.CBS_BUURTKAART_2022_VERSIE3
        WHERE buurtcode = '@Value(buurtcode)'
      ),

      bomen_in_buurt AS (
        SELECT
          b.CROWN_AREA
        FROM BODEM.BOMEN_KRONEN b
        JOIN buurt_geom g
          ON b.SHAPE.STIntersects(g.buurt_shape) = 1
      )

      SELECT
        '@Value(buurtcode)' AS buurtcode,
        SUM(CROWN_AREA) AS totaal_kroonoppervlak_m2
      FROM bomen_in_buurt;
    RESULT -> AttributeExposer_2
    <REJECTED> -> Logger_2
AttributeExposer_2
    ATTR_TABLE = buurtcode,,totaal_kroonoppervlak_m2,
    -> FeatureJoiner_2 [RIGHT]
FeatureJoiner_2
    ATTR_CONFLICT_RES_LOOKUP = USE_LEFT
    GEOMETRY_HANDLING_LOOKUP = USE_LEFT
    JOIN_KEYS = buurtcode buurtcode AUTO
    JOIN_MODE = Inner
    ATTR_CONFLICT_RES = Prefer Left
    GEOMETRY_HANDLING = Prefer Left
    JOINED -> AttributeManager_3
AttributeManager_3
    ATTR_TABLE:
      SET_TO Percentage groen (real64) = @Evaluate((@Value(totaal_kroonoppervlak_m2)/100)/@Value(oppervlakte_land_in_ha))
      SET_TO
    -> FeatureClass_buurt (writer GEODATABASE_FILE_1)
FeatureClass_buurt (writer GEODATABASE_FILE_1)
    attributes: wijkcode char(2048), gemeentecode char(2048), gemeentenaam char(2048), indelingswijziging_wijken_en_buurten integer, water char(2048), omgevingsadressendichtheid integer, stedelijkheid_adressen_per_km2 integer, bevolkingsdichtheid_inwoners_per_km2 integer, aantal_inwoners integer, mannen integer, vrouwen integer, percentage_personen_0_tot_15_jaar integer, percentage_personen_15_tot_25_jaar integer, percentage_personen_25_tot_45_jaar integer, percentage_personen_45_tot_65_jaar integer, percentage_personen_65_jaar_en_ouder integer, percentage_ongehuwd integer, percentage_gehuwd integer, percentage_gescheid integer, percentage_verweduwd integer, geboorte_totaal integer, geboortes_per_1000_inwoners integer, sterfte_totaal integer, sterfte_relatief integer, aantal_huishoudens integer, percentage_eenpersoonshuishoudens integer, percentage_huishoudens_zonder_kinderen integer, percentage_huishoudens_met_kinderen integer, gemiddelde_huishoudsgrootte double, percentage_met_herkomstland_nederland integer,
      percentage_met_herkomstland_uit_europa_excl_nl integer, percentage_met_herkomstland_buiten_europa integer, percentage_geb_in_nl_met_herkomstland_nederland integer, perc_geb_in_nl_met_herkomstland_in_europa_ex_nl integer, perc_geb_in_nl_met_herkomstland_buiten_europa integer, perc_geb_buiten_nl_met_herkomstlnd_in_europa_ex_nl integer, perc_geb_buiten_nl_met_herkomstlnd_buiten_europa integer, aantal_bedrijven_landbouw_bosbouw_visserij integer, aantal_bedrijven_nijverheid_energie integer, aantal_bedrijven_handel_en_horeca integer, aantal_bedrijven_vervoer_informatie_communicatie integer, aantal_bedrijven_financieel_onroerend_goed integer, aantal_bedrijven_zakelijke_dienstverlening integer, aantal_bedrijven_overheid_onderwijs_en_zorg integer, aantal_bedrijven_cultuur_recreatie_overige integer, aantal_bedrijfsvestigingen integer, woningvoorraad integer, gemiddelde_woningwaarde integer, percentage_eengezinswoning integer, percentage_meergezinswoning integer, percentage_bewoond integer, percentage_koopwoningen integer, percentage_huurwoningen integer, perc_huurwoningen_in_bezit_woningcorporaties integer, perc_huurwoningen_in_bezit_overige_verhuurders integer, percentage_woningen_met_eigendom_onbekend integer, percentage_bouwjaarklasse_tot_2000 integer, percentage_bouwjaarklasse_vanaf_2000 integer, percentage_leegstand_woningen integer, gemiddeld_gasverbruik_totaal integer,
      gemiddeld_gasverbruik_appartement integer, gemiddeld_gasverbruik_tussenwoning integer, gemiddeld_gasverbruik_hoekwoning integer, gemiddeld_gasverbruik_2_onder_1_kap_woning integer, gemiddeld_gasverbruik_vrijstaande_woning integer, gemiddeld_gasverbruik_huurwoning integer, gemiddeld_gasverbruikkoopwoning integer, gemiddeld_elektriciteitsverbruik_totaal integer, gemiddeld_elektriciteitsverbruik_appartement integer, gemiddeld_elektriciteitsverbruik_tussenwoning integer, gemiddeld_elektriciteitsverbruik_hoekwoning integer, gem_elektriciteitsverbruik_2_onder_1_kap_woning integer, gem_elektriciteitsverbruik_vrijstaande_woning integer, gemiddeld_elektriciteitsverbruik_huurwoning integer, gemiddeld_elektriciteitsverbruikkoopwoning integer, percentage_woningen_met_stadsverwarming integer, opleidingsniveau_laag integer, opleidingsniveau_middelbaar integer, opleidingsniveau_hoog integer, netto_arbeidsparticipatie integer, percentage_werknemers integer, percentage_zelfstandigen integer, aantal_inkomensontvangers integer, gemiddeld_inkomen_per_inkomensontvanger integer, gemiddeld_inkomen_per_inwoner integer, percentage_personen_met_hoog_inkomen integer, percentage_personen_met_laag_inkomen integer, percentage_huishoudens_met_hoog_inkomen integer, percentage_huishoudens_met_laag_inkomen integer, percentage_huishoudens_met_laagste_inkomen integer,
      percentage_huishoudens_onder_of_rond_sociaal_minimum integer, aantal_personen_met_een_ao_uitkering_totaal integer, aantal_personen_met_een_ww_uitkering_totaal integer, aantal_personen_met_een_alg_bijstandsuitkering_tot integer, aantal_personen_met_een_aow_uitkering_totaal integer, gemiddeld_gestandaardiseerd_inkomen_van_huishoudens double, huishoudens_tot_110_percent_van_sociaal_minimum double, huishoudens_tot_120_percent_van_sociaal_minimum double, mediaan_vermogen_van_particuliere_huish double, aantal_jongeren_met_jeugdzorg_in_natura integer, percentage_jongeren_met_jeugdzorg_in_natura double, aantal_wmo_clienten integer, aantal_wmo_clienten_per_1000_inwoners integer, personenautos_totaal integer, personenautos_per_huishouden double, personenautos_per_km2 integer, motortweewielers_totaal integer, aantal_personenautos_met_brandstof_benzine integer, aantal_personenautos_met_overige_brandstof integer, oppervlakte_totaal_in_ha integer, oppervlakte_land_in_ha integer, oppervlakte_water_in_ha integer, huisartsenpraktijk_gemiddelde_afstand_in_km double, huisartsenpraktijk_gemiddeld_aantal_binnen_1_km double, huisartsenpraktijk_gemiddeld_aantal_binnen_3_km double, huisartsenpraktijk_gemiddeld_aantal_binnen_5_km double, huisartsenpost_gemiddelde_afstand_in_km double, apotheek_gemiddelde_afstand_in_km double, ziekenhuis_incl_buitenpolikliniek_gem_afst_in_km double, ziekenhuis_incl_buitenpoli_gem_aantal_binnen_5_km double,
      ziekenhuis_incl_buitenpoli_gem_aantal_binnen_10_km double, ziekenhuis_incl_buitenpoli_gem_aantal_binnen_20_km double, ziekenhuis_excl_buitenpolikliniek_gem_afst_in_km double, ziekenhuis_excl_buitenpoli_gem_aantal_binnen_5_km double, ziekenhuis_excl_buitenpoli_gem_aantal_binnen_10_km double, ziekenhuis_excl_buitenpoli_gem_aantal_binnen_20_km double, grote_supermarkt_gemiddelde_afstand_in_km double, grote_supermarkt_gemiddeld_aantal_binnen_1_km double, grote_supermarkt_gemiddeld_aantal_binnen_3_km double, grote_supermarkt_gemiddeld_aantal_binnen_5_km double, winkels_ov_dagelijkse_levensm_gem_afst_in_km double, winkels_ov_dagel_levensm_gem_aantal_binnen_1_km double, winkels_ov_dagel_levensm_gem_aantal_binnen_3_km double, winkels_ov_dagel_levensm_gem_aantal_binnen_5_km double, warenhuis_gemiddelde_afstand_in_km double, warenhuis_gemiddeld_aantal_binnen_5_km double, warenhuis_gemiddeld_aantal_binnen_10_km double, warenhuis_gemiddeld_aantal_binnen_20_km double, cafe_gemiddelde_afstand_in_km double, cafe_gemiddeld_aantal_binnen_1_km double, cafe_gemiddeld_aantal_binnen_3_km double, cafe_gemiddeld_aantal_binnen_5_km double, cafetaria_gemiddelde_afstand_in_km double, cafetaria_gemiddeld_aantal_binnen_1_km double, cafetaria_gemiddeld_aantal_binnen_3_km double, cafetaria_gemiddeld_aantal_binnen_5_km double, restaurant_gemiddelde_afstand_in_km double, restaurant_gemiddeld_aantal_binnen_1_km double, restaurant_gemiddeld_aantal_binnen_3_km double, restaurant_gemiddeld_aantal_binnen_5_km double,
      hotel_gemiddelde_afstand_in_km double, hotel_gemiddeld_aantal_binnen_5_km double, hotel_gemiddeld_aantal_binnen_10_km double, hotel_gemiddeld_aantal_binnen_20_km double, kinderdagverblijf_gemiddelde_afstand_in_km double, kinderdagverblijf_gemiddeld_aantal_binnen_1_km double, kinderdagverblijf_gemiddeld_aantal_binnen_3_km double, kinderdagverblijf_gemiddeld_aantal_binnen_5_km double, buitenschoolse_opvang_gem_afstand_in_km double, buitenschoolse_opvang_gemiddeld_aantal_binnen_1_km double, buitenschoolse_opvang_gemiddeld_aantal_binnen_3_km double, buitenschoolse_opvang_gemiddeld_aantal_binnen_5_km double, basisonderwijs_gemiddelde_afstand_in_km double, basisonderwijs_gemiddeld_aantal_binnen_1_km double, basisonderwijs_gemiddeld_aantal_binnen_3_km double, basisonderwijs_gemiddeld_aantal_binnen_5_km double, voortgezet_onderwijs_gem_afstand_in_km double, voortgezet_onderwijs_gemiddeld_aantal_binnen_3_km double, voortgezet_onderwijs_gemiddeld_aantal_binnen_5_km double, voortgezet_onderwijs_gemiddeld_aantal_binnen_10_km double, vmbo_gemiddelde_afstand_in_km double, vmbo_gemiddeld_aantal_binnen_3_km double, vmbo_gemiddeld_aantal_binnen_5_km double, vmbo_gemiddeld_aantal_binnen_10_km double, havo_vwo_gemiddelde_afstand_in_km double, havo_vwo_gemiddeld_aantal_binnen_3_km double, havo_vwo_gemiddeld_aantal_binnen_5_km double, havo_vwo_gemiddeld_aantal_binnen_10_km double, brandweerkazerne_gemiddelde_afstand_in_km double, oprit_hoofdverkeersweg_gemiddelde_afstand_in_km double,
      treinstation_gemiddelde_afstand_in_km double, overstapstation_gemiddelde_afstand_in_km double, zwembad_gemiddelde_afstand_in_km double, kunstijsbaan_gemiddelde_afstand_in_km double, bibliotheek_gemiddelde_afstand_in_km double, poppodium_gemiddelde_afstand_in_km double, bioscoop_gemiddelde_afstand_in_km double, bioscoop_gemiddeld_aantal_binnen_5_km double, bioscoop_gemiddeld_aantal_binnen_10_km double, bioscoop_gemiddeld_aantal_binnen_20_km double, sauna_gemiddelde_afstand_in_km double, zonnebank_gemiddelde_afstand_in_km double, attractiepark_gemiddelde_afstand_in_km double, attractiepark_gemiddeld_aantal_binnen_10_km double, attractiepark_gemiddeld_aantal_binnen_20_km double, attractiepark_gemiddeld_aantal_binnen_50_km double, theater_gemiddelde_afstand_in_km double, theater_gemiddeld_aantal_binnen_5_km double, theater_gemiddeld_aantal_binnen_10_km double, theater_gemiddeld_aantal_binnen_20_km double, gemiddelde_afstand_tot_museum double, gemiddeld_aantal_musea_binnen_5_km double, gemiddeld_aantal_musea_binnen_10_km double, gemiddeld_aantal_musea_binnen_20_km double, afstand_tot_openbaar_groen_totaal double, afstand_tot_park_of_plantsoen double, afstand_tot_dagrcreatief_terrein double, afstand_tot_bos double, afstand_tot_open_natuur_terrein_totaal double, afstand_tot_open_droog_natuur_terrein double,
      afstand_tot_open_nat_natuurlijk_terrein double, afstand_tot_semiopenbaar_groen_totaal double, afstand_tot_sportterrein double, afstand_tot_volkstuin double, afstand_tot_verblijfsrecreatief_terrein double, afstand_tot_recreatief_binnenwater double, afstand_tot_begraafplaats double, jrstatcode char(2048), jaar integer, fid bigint, totaal_kroonoppervlak_m2 char(200), Percentage_groen double, buurtcode char(2048), buurtnaam char(2048), meest_voorkomende_postcode char(2048), dekkingspercentage integer
Logger_2
    LOG_FEATURE = LOG_ONLY
    MAXCOORDS = 20
    MAXFEATS = 20
    MESSAGE = Feature is:
    SEVERITY = INFO
