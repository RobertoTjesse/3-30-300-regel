FME workspace 300_2025.fmw

Parameters:
- Gemeente = 'Delft'   # Selecteer de gemeente(s) die je wilt analyseren
- VALHALLA_URL =   # Type het adres waar valhalla op draait

Creator
    GEOMTYPE = Geometry Object
    NUM = 1
    CREATED -> FeatureReader_5 [INITIATOR]
FeatureReader_5
    ATTRIBUTES =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
    ATTR_ACCUM_MODE = Only Use Result
    CLIP_TO_ENVELOPE = NO
    COMBINE_GEOM = Use Result
    DATASET = $(FME_MF_DIR_ENCODED)fme input\Panden\wijkenbuurten_2023.gpkg
    FEATURETYPES = wijken
    FORMAT = OGCGEOPACKAGE
    GEOMETRY_TYPES = buurten,"""geom,fme_area""",gemeenten,"""geom,fme_area""",wijken,"""geom,fme_area"""
    INITIATOR_FIRST_OUTPUT = default
    INTERACT = NONE
    OGCGEOPACKAGE_ENCODE_FEATURE_TYPE_AND_ATTR_NAMES = YES
    OGCGEOPACKAGE_ENFORCE_FOREIGN_KEY_INTEGRITY = YES
    OGCGEOPACKAGE_EXPOSE_PRIMARY_KEY_ATTRIBUTE = YES
    OGCGEOPACKAGE_OPEN_SINGLE_RASTER_AS_SUBDATASET = YES
    OGCGEOPACKAGE_QUERY_FEATURE_TYPES_FOR_MERGE_FILTERS = Yes
    OGCGEOPACKAGE_READER_REPLACE_INVALID_CHARS = NO
    OGCGEOPACKAGE_READ_BOOLEANS_AS_YES_NO = YES
    OGCGEOPACKAGE_READ_NULLS = YES
    OGCGEOPACKAGE_USE_SEARCH_ENVELOPE = NO
    ORDER_RESULTS = No
    OUTPUT_ADD_SCHEMA_ATTRIBUTES = NO
    OUTPUT_FEATURES_DISPLAY = Schema and Data Features
    WHERE = "gemeentenaam"=$(Gemeente)
    wijken -> FeatureReader [INITIATOR]
Reprojector_2
    DEST = EPSG:28992
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> Clipper [CANDIDATE]

Bookmark: vervange door usr parameters
Note: moet nog worden gweselcteerd
FeatureReader
    ATTRIBUTES = groen_uit_osm_top10_2024,"OBJECTID,type,bron,_area,Shape_Length,Shape_Area"
    ATTR_ACCUM_MODE = Only Use Result
    CLIP_TO_ENVELOPE = NO
    COMBINE_GEOM = Use Result
    DATASET = $(FME_MF_DIR_ENCODED)fme input\Groenvoorzierningen\groenkaart.gdb
    FEATURETYPES = groen_uit_osm_top10_2024
    FORMAT = GEODATABASE_FILE
    GEODATABASE_FILE_ALIAS_MODE = NONE
    GEODATABASE_FILE_CACHE_MULTIPATCH_TEXTURES = yes
    GEODATABASE_FILE_CHECK_SIMPLE_GEOM = no
    GEODATABASE_FILE_CREATE_FEATURE_TABLES_FROM_DATA = Yes
    GEODATABASE_FILE_DISABLE_FEATURE_DATASET_ATTRIBUTE = Yes
    GEODATABASE_FILE_FEATURE_READ_MODE = Features
    GEODATABASE_FILE_IGNORE_NETWORK_INFO = yes
    GEODATABASE_FILE_IGNORE_RELATIONSHIP_INFO = yes
    GEODATABASE_FILE_MERGE_FEAT_LINKED_ANNOS = no
    GEODATABASE_FILE_QUERY_FEATURE_TYPES_FOR_MERGE_FILTERS = Yes
    GEODATABASE_FILE_READ_THREE_POINT_ARCS = no
    GEODATABASE_FILE_REMOVE_FEATURE_DATASET = NO
    GEODATABASE_FILE_RESOLVE_DOMAINS = no
    GEODATABASE_FILE_RESOLVE_SUBTYPE_NAMES = yes
    GEODATABASE_FILE_SIMPLE_DONUT_GEOMETRY = no
    GEODATABASE_FILE_SPLIT_COMPLEX_ANNOS = no
    GEODATABASE_FILE_SPLIT_COMPLEX_EDGES = no
    GEODATABASE_FILE_SPLIT_MULTI_PART_ANNOS = no
    GEODATABASE_FILE_STRIP_GUID_GLOBALID_BRACES = no
    GEODATABASE_FILE_TRANSLATE_SPATIAL_DATA_ONLY = no
    GEODATABASE_FILE_USE_SEARCH_ENVELOPE = NO
    GEOMETRY_TYPES = groen_uit_osm_top10_2024,"""Shape,fme_area"""
    INITIATOR_FIRST_OUTPUT = default
    INTERACT = INTERSECTS
    ORDER_RESULTS = No
    OUTPUT_ADD_SCHEMA_ATTRIBUTES = NO
    OUTPUT_FEATURES_DISPLAY = Schema and Data Features
    WHERE = "bron" <> 'top 10 water'
    groen_uit_osm_top10_2024 -> Reprojector_3
Reprojector_3
    DEST = Amersfoort-RDNew
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> Tester
Tester
    BOOL_OP = COMPOSITE
    COMPOSITE_TEST = 1 AND 2
    TEST_CLAUSE:
      TEST @Value(_area) >= 300
      TEST @Evaluate(@Value(Shape_Length)/@Value(Shape_Area) ) <= 0,35
    TEST_MODE = TEST
    PASSED -> Clipper [CLIPPER]
    PASSED -> GeometryCoercer

Bookmark: Ingangen van parken extraheren
GeometryCoercer
    GQUERY:
      for $geom in //geometry
      where $geom/count(parent::geometry) = 0
      return number($geom/@fme_id)
    KIND = fme_line
    COERCED -> LineOnLineIntersectionAngle [LinesRequestor]
Clipper
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_PARTS
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> LineOnLineIntersectionAngle [LinesSupplier]
LineOnLineIntersectionAngle
    DECIMAL_PLACES = 2
    IntersectionPoints -> Counter
Counter
    CNT_ATTR = id
    DOMAIN = counter
    SCOPE = Global
    START = 0
    -> Reprojector
Reprojector
    DEST = EPSG:4326
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> VertexExtractor
VertexExtractor
    Point -> AttributeManager_2

Bookmark: Postgis database op Azure. Hier maak ik een buffer van 300 meter rondom de gemeente X, haal ik alle lopende wegen als polylines
SQLCreator
    DATASET = osm_reader_20250509
    FORMAT = POSTGIS
    OUTPUT_FEATURES = DATA_ONLY
    POSTGIS_CREATE_FEATURE_TABLES_FROM_DATA = Yes
    POSTGIS_DISABLE_COLLECTION_SPLITTING = yes
    POSTGIS_NAMED_CONNECTION = osm_reader_20250509
    POSTGIS_QUERY_FEATURE_TYPES_FOR_MERGE_FILTERS = Yes
    POSTGIS_READ_TIME_WITH_TIMEZONE = Yes
    POSTGIS_SCHEMAS_FOR_TABLE_LISTING = osm_data
    POSTGIS_USE_TRUE_POSTGIS_TYPES = yes
    SQL_STATEMENT:
      WITH gemeente_poly AS (
        SELECT ST_Buffer(ST_MakePolygon(way), 300) AS geom
        FROM osm_data.planet_osm_line
        WHERE boundary = 'administrative'
          AND admin_level = '8'
          AND name = $(Gemeente)
      )

      SELECT
        ST_Intersection(l.way, g.geom) AS geom,
        l.osm_id,
        l.highway
      FROM osm_data.planet_osm_line l, gemeente_poly g
      WHERE ST_Intersects(l.way, g.geom)
        AND l.highway IN (
          'footway', 'path', 'pedestrian', 'residential',
          'living_street', 'cycleway', 'steps', 'track',
          'service', 'unclassified', 'tertiary', 'tertiary_link',
          'bridleway', 'corridor', 'pathway', 'bus_guideway'
        )
        AND ST_Intersection(l.way, g.geom) IS NOT NULL
        AND GeometryType(ST_Intersection(l.way, g.geom)) IN ('LINESTRING', 'MULTILINESTRING');
    RESULT -> Reprojector_2

Bookmark: JSON builder
AttributeManager_2
    ATTR_TABLE:
      REMOVE _z (buffer)
      SET_TO coordinate_pairs (varchar(200)) = {"lat":@round(@Value(_y),7),"lon":@round(@Value(_x),7)}
    -> ListBuilder_2
ListBuilder_2
    GROUP_BY = id
    LIST_ATTRS_TO_INCLUDE = coordinate_pairs
    LIST_NAME = locations
    -> ListConcatenator
ListConcatenator
    DROP_EMPTY_PARTS = No
    LIST_ATTR = locations{}.coordinate_pairs
    SEP = ,
    VAL_ATTR = _concatenated
    -> JSONTemplater [ROOT]
JSONTemplater
    RESULT_ATTRIBUTE = _result
    ROOT_QUERY_EXPR:
      {
        "id": "@Value(id)",
        "locations":fme:get-attribute("_concatenated"),
        "costing": "pedestrian",
        "contours": [{ "time": 5, "color": "ff0000" }],
        "polygons": true
      }
    VISIBLE_QUERY_VALIDATE = Yes
    -> AttributeManager
AttributeManager
    ATTR_TABLE:
      SET_TO request (varchar(200)) = {
          "id": @Value(id),
          "locations": [
            @Value(_concatenated)
          ],
          "costing": "pedestrian",
          "contours": [
            { "time": 5, "color": "ff0000" }
          ],
          "polygons": true
        }
    -> HTTPCaller

Bookmark: Valhalla API
HTTPCaller
    CLIENT_CERTIFICATE_TYPE = NONE
    CONNECTION_TIMEOUT_LENGTH = 60
    CONTENT_TYPE_LOOKUP = application/json
    ERROR_ATTR = _error
    FOLLOW_REDIRECTS = FOLLOW_WITH_GET
    HTTP_METHOD = POST
    MAX_HTTP_VERSION = HTTP_2
    MAX_TRANSFERS_IN_PROGRESS = 25
    MINIMUM_ENCRYPTION_LEVEL = OS_DEFAULT
    RATE_LIMIT_INTERVAL_IN_SECONDS = 10
    RATE_LIMIT_MAX_REQUESTS = 10
    RATE_LIMIT_REQUEST_TIMING = SPREAD
    REDIRECT_AUTH = ORIGINAL_DOMAIN_ONLY
    RESPONSE_TYPE = Attribute
    RETRY_FAILED_TRANSFERS = CONNECTION 429 500 501 502 503 504 505 506 507 508 509 510 511 400 401 402 403 404 405 406 407 408 409 410 411 412 413 414 415 416 417 418 421 422 423 424 425 426 428 431 451
    RETRY_INITIAL_BACKOFF = 500
    RETRY_MAX_RETRIES = 3
    SPLIT_MULTIPART_DOWNLOADS = NO
    STATUS_CODE_ATTR = _http_status_code
    TARGET_ATTR = _response_body
    TARGET_ATTR_ENCODING = auto-detect
    TARGET_URL = $(VALHALLA_URL)/isochrone
    TRANSFER_TIMEOUT_LENGTH = 90
    UPLOAD_BODY = @Value(request)
    UPLOAD_TYPE = STRING_UPLOAD
    USE_COOKIES = No
    VERIFY_SSL_CERTIFICATES = Yes
    UPLOAD_CONTENT_TYPE = JSON (application/json)
    -> GeometryReplacer
GeometryReplacer
    KIND = GEOJSON
    REMOVE_ATTRIBUTE = Yes
    SOURCE = @Value(_response_body)
    KIND_LONG = GeoJSON
    -> GeometryReplacer_Output
GeometryReplacer_Output: Inspector

FME custom transformer HorizontalAngleCalculator
Overview
Description
This transformer calculates the angle and azimuth of any input line, polyline, or line created by connecting two input points. Angles are measured from the reference point of east (east-0, counter-clockwise positive). The azimuth is the angle between the line and the north vector (north-0, clockwise positive). Output measurement is either degrees, radians, or milliradians (trigonometric).
Notes: 
For polylines it returns the angle and azimuth of a line connecting the first and the last vertices of the polyline. For retrieving information about each segment of the polyline use PolylineAnalyzer.
This transformer replaces the AzimuthCalculator.
Keywords: Bearing, Heading
Input Ports
Input features must contain valid line geometry, or values specifying two endpoints of a line.
Output Ports
Output: Features are output with new attributes containing the angle and azimuth of the line or polyline.
_angle: Angles increase counterclockwise from the reference point of east (which represents zero degrees).
_azimuth: Azimuth values increase clockwise from the reference point of north (which represents zero degrees).
Rejected: Any features that are not valid line geometry, or are loops (coincident start and end points), will be passed through this port. Rejected features are output with value INVALID_GEOMETRY_TYPE stored in the fme_rejection_code attribute.
If angles will be calculated from input points, then any features missing all of the x- and y-values are output with value MISSING_PARAMETER_XY_VALUE stored in the fme_rejection_code, or, if an attribute value cannot be resolved as a coordinate, then features are output with value INVALID_PARAMETER_XY_VALUE stored in the fme_rejection_code.
Parameters
Calculate Angle from: (Feature, Specified) This parameter will determine whether to calculate the angle and azimuth from the geometry of a feature or set of features (points, lines, polylines), or to calculate from a line created by connecting to input points.
Point 1 X-Coord: Specify a float or attribute containing a valid x-coordinate.
Point 1 Y-Coord: Specify a float or attribute containing a valid y-coordinate.
Point 2 X-Coord: Specify a float or attribute containing a valid x-coordinate.
Point 2 Y-Coord: Specify a float or attribute containing a valid y-coordinate.
Angle Unit Measurement: (Degrees, Radians) This parameter sets the unit measurement of the output angle and azimuth.

Parameters:
- GeneralBox =   # General
- UNIT_OUTPUT = DEG   # Angle Unit Measurement
- ANGLE_TYPE = Feature   # Calculate Angle from
- SpecifiedBox =   # Specified Coordinates
- COORD1 =   # Point 1 X-Coord
- COORD1Y =   # Point 1 Y-Coord
- COORD2 =   # Point 2 X-Coord
- COORD2Y =   # Point 2 Y-Coord

Input (input)
    -> TestFilter
AttributeRemover_3: Junction
    -> Tester
Output (output)
<Rejected> (output)

Bookmark: Parse Incoming Features for Validity
TestFilter
    DEFAULT_VALUE = AngleFrom_AsSpecified
    PASSED_TEST_GROUP_OUTPUT = FIRST
    TEST_LIST = BOOL_OP,OR,COMPOSITE_TEST,<Unused>,TEST_CLAUSE,"TEST $(ANGLE_TYPE) = Feature",AngleFrom_Feature
    AngleFrom_Feature -> GeometryFilter
    AngleFrom_AsSpecified -> ParameterFetcher
GeometryFilter
    FILTER_MODE = COMPLETE
    FILTER_MULTI = FILTER_TYPES]"Point MultiPoint Line Clothoid OrientedArc Path MultiCurve"]INSTANCES]INSTANCE]FME_CONTROLLER_QUERY_FILE]]FME_CONTROLLER_CHOICE]Complete
    Point -> CoordinateExtractor_3
    MultiPoint -> CoordinateExtractor_3
    Line -> LoopFilter_FeatureMode [LINE]
    Clothoid -> LoopFilter_FeatureMode [LINE]
    OrientedArc -> LoopFilter_FeatureMode [LINE]
    Path -> LoopFilter_FeatureMode [LINE]
    MultiCurve -> LoopFilter_FeatureMode [LINE]
CoordinateExtractor_3
    IND = 0
    RECURSIVE = No
    X_ATTR = _X
    Y_ATTR = _Y
    MODE = Specify Coordinate
    -> ExpressionEvaluator_2
    <REJECTED> -> LoopFilter_FeatureMode [LINE]
LoopFilter_FeatureMode
    PASSED -> AttributeCreator_3
    FAILED -> CoordinateExtractor
CoordinateExtractor
    IND = 0
    RECURSIVE = No
    X_ATTR = _X1
    Y_ATTR = _Y1
    Z_DEFAULT = -9999
    MODE = Specify Coordinate
    -> CoordinateExtractor_2
CoordinateExtractor_2
    IND = -1
    RECURSIVE = No
    X_ATTR = _X2
    Y_ATTR = _Y2
    Z_DEFAULT = -9999
    MODE = Specify Coordinate
    -> ExpressionEvaluator_6
ParameterFetcher
    ATTR_LIST = _X1 {$(COORD1)} _Y1 {$(COORD1Y)} _X2 {$(COORD2)} _Y2 {$(COORD2Y)}
    -> Tester_hasValue
Tester_hasValue
    BOOL_OP = COMPOSITE
    COMPOSITE_TEST = 1 AND 2 AND 3 AND 4
    TEST_CLAUSE:
      TEST _X1 ATTRIBUTE_HAS_A_VALUE ""
      TEST _X2 ATTRIBUTE_HAS_A_VALUE ""
      TEST _Y1 ATTRIBUTE_HAS_A_VALUE ""
      TEST _Y2 ATTRIBUTE_HAS_A_VALUE ""
    TEST_MODE = TEST
    PASSED -> Tester_Numeric
    FAILED -> AttributeCreator
Tester_Numeric
    BOOL_OP = COMPOSITE
    COMPOSITE_TEST = 1 AND 2 AND 3 AND 4
    TEST_CLAUSE:
      TEST @Value(_X1) TYPE NUM
      TEST @Value(_X2) TYPE NUM
      TEST @Value(_Y1) TYPE NUM
      TEST @Value(_Y2) TYPE NUM
    TEST_MODE = TEST
    PASSED -> VertexCreator_Point1
    PASSED -> VertexCreator_Point2
    FAILED -> AttributeCreator_2
VertexCreator_Point1
    MEASURE_TYPE_LOOKUP = CONTINUOUS
    MODE = REPLACE
    REMOVE_ATTRIBUTES = No
    XVAL = @Value(_X1)
    YVAL = @Value(_Y1)
    MEASURE_TYPE = Continuous
    MODE_NAME = Replace with Point
    -> LineBuilder
VertexCreator_Point2
    MEASURE_TYPE_LOOKUP = CONTINUOUS
    MODE = REPLACE
    REMOVE_ATTRIBUTES = No
    XVAL = @Value(_X2)
    YVAL = @Value(_Y2)
    MEASURE_TYPE = Continuous
    MODE_NAME = Replace with Point
    -> Decelerator
Decelerator
    DECEL_LOOKUP = PERFEATDELAY
    DELAY = 0.5
    DECEL_TYPE = Per Feature Delay
    -> LineBuilder
LineBuilder
    ACCUM_INPUT_ATTRS_LOOKUP = All
    REMOVE_DUPLICATES_LOOKUP = NO
    ACCUM_INPUT_ATTRS = Merge Incoming Attributes
    REMOVE_DUPLICATES = No
    LINE -> LoopFilter_SpecifiedMode [LINE]
LoopFilter_SpecifiedMode
    PASSED -> AttributeCreator_3
    FAILED -> ExpressionEvaluator_5

Bookmark: Angle Calculations
ExpressionEvaluator_2
    ACTION = Create New Attribute
    EXPRESSION = @atan2(@Value(_Y),@Value(_X))
    VAL_ATTR = _angleRad
    -> TestFilter_2
ExpressionEvaluator_6
    ACTION = Create New Attribute
    EXPRESSION = @atan2(@Value(_Y2)-@Value(_Y1),@Value(_X2)-@Value(_X1))
    VAL_ATTR = _angleRad
    -> TestFilter_2
ExpressionEvaluator_5
    ACTION = Create New Attribute
    EXPRESSION = @atan2(@Value(_Y2)-@Value(_Y1),@Value(_X2)-@Value(_X1))
    VAL_ATTR = _angleRad
    -> TestFilter_2

Bookmark: Azimuth Calculations
TestFilter_2
    DEFAULT_VALUE = <=90
    PASSED_TEST_GROUP_OUTPUT = FIRST
    TEST_LIST = "BOOL_OP,OR,COMPOSITE_TEST,""""""1"""""",TEST_CLAUSE,TEST @Evaluate(@radToDeg(@Value(_angleRad))) > 90",>90
    >90 -> ExpressionEvaluator_3
    <=90 -> ExpressionEvaluator_4
ExpressionEvaluator_3
    ACTION = Create New Attribute
    EXPRESSION = 450-@radToDeg(@Value(_angleRad))
    VAL_ATTR = _azimuthDeg
    -> AttributeRemover_3
ExpressionEvaluator_4
    ACTION = Create New Attribute
    EXPRESSION = 90 - @radToDeg(@Value(_angleRad))
    VAL_ATTR = _azimuthDeg
    -> AttributeRemover_3

Bookmark: Cleanup and Set Units
Tester
    BOOL_OP = OR
    TEST_CLAUSE = TEST @Value(_angleRad) < 0
    TEST_MODE = TEST
    PASSED -> ExpressionEvaluator_8
    FAILED -> ExpressionEvaluator_7
ExpressionEvaluator_8
    ACTION = Create New Attribute
    EXPRESSION = 360 + @radToDeg(@Value(_angleRad))
    VAL_ATTR = _angle
    -> TestFilter_3
ExpressionEvaluator_7
    ACTION = Create New Attribute
    EXPRESSION = @radToDeg(@Value(_angleRad))
    VAL_ATTR = _angle
    -> TestFilter_3
TestFilter_3
    DEFAULT_VALUE = Degrees
    PASSED_TEST_GROUP_OUTPUT = FIRST
    TEST_LIST = BOOL_OP,OR,COMPOSITE_TEST,<Unused>,TEST_CLAUSE,"TEST $(UNIT_OUTPUT) = RAD",Radians
    Radians -> AttributeManager
    Degrees -> AttributeManager_2
AttributeManager
    ATTR_TABLE:
      REMOVE _angleRad (real64)
      RENAME_SET_VALUE _azimuthDeg > _azimuth (real64) = @Evaluate(@degToRad(@Value(_azimuth)))
      REMOVE _X1 (real64)
      REMOVE _Y1 (real64)
      REMOVE _X2 (real64)
      REMOVE _Y2 (real64)
      SET_TO _angle (real64) = @Evaluate(@degToRad(@Value(_angle)))
    -> Output (output)
AttributeManager_2
    ATTR_TABLE:
      REMOVE _angleRad (real64)
      REMOVE _X1 (real64)
      REMOVE _Y1 (real64)
      REMOVE _X2 (real64)
      REMOVE _Y2 (real64)
      RENAME_SET_VALUE _azimuthDeg > _azimuth (real64)
    -> Output (output)

Bookmark: Handle <Rejected> Features
AttributeCreator_3
    ATTR_TABLE = SET_TO fme_rejection_message (varchar(200)) = FEATURE IS A LOOP
    -> AttributeCreator_4
AttributeCreator_4
    ATTR_TABLE = SET_TO fme_rejection_code (varchar(200)) = INVALID_GEOMETRY_TYPE
    -> _Rejected_
AttributeCreator_2
    ATTR_TABLE = SET_TO fme_rejection_code (varchar(200)) = INVALID_PARAMETER_XY_VALUE
    -> _Rejected_
AttributeCreator
    ATTR_TABLE = SET_TO fme_rejection_code (varchar(200)) = MISSING_PARAMETER_XY_VALUE
    -> _Rejected_
_Rejected_: Junction
    -> AttributeRemover
AttributeRemover
    REMOVE_ATTRS = _Y1,_Y2,_X1,_X2
    -> <Rejected> (output)

FME custom transformer LineOnLineIntersectionAngle
Gives the points of intersection of two streams of lines with the angle at which they cross.

Parameters:
- DECIMAL_PLACES = 2   # Decimal places

LinesRequestor (input)
    -> Counter
Note: Create a local temporary Id for each line.
Counter
    CNT_ATTR = Id_requestor
    SCOPE = Local
    START = 0
    -> LineOnLineOverlayer [LINE]
    -> FeatureMerger [REQUESTOR]
LinesSupplier (input)
    -> Counter_2
Note: Create a local temporary Id for each line.
Counter_2
    CNT_ATTR = Id_supplier
    SCOPE = Local
    START = 0
    -> LineOnLineOverlayer [LINE]
    -> FeatureMerger_2 [REQUESTOR]
Note: Find the intersection points. Merge all attributes.
LineOnLineOverlayer
    ATTRS_ACCUM_MODE_LOOKUP = ALL
    CLEANING_TOLERANCE_LOOKUP = AUTO
    DEAGGREGATE_INPUT = Yes
    GENERATE_LIST_DROP = NO
    OV_ATTR = _overlaps
    SEPARATE_COLLINEAR_SEGMENTS = No
    ATTRS_ACCUM_MODE = Merge Attributes
    CLEANING_TOLERANCE = Automatic
    POINT -> TestFilter
    LINE -> Clipper [CANDIDATE]
Note: Intersection is found between requestor and supplier if both requestor_id and supplier_id have a value.
TestFilter
    DEFAULT_VALUE = <UNFILTERED>
    PASSED_TEST_GROUP_OUTPUT = FIRST
    TEST_LIST:
      "BOOL_OP,AND,COMPOSITE_TEST,""""""1 AND 2"""""",TEST_CLAUSE,TEST Id_requestor ATTRIBUTE_HAS_A_VALUE ""
      TEST Id_supplier ATTRIBUTE_HAS_A_VALUE """,has intersection
    has intersection -> Bufferer
    has intersection -> PointOnLineOverlayer [POINT]
Note: Made by Warre Gevers at Nordend.
Note: Create buffer around intersection point
Bufferer
    ANGLE = 22.5
    CAP_STYLE_LOOKUP = CAP_ARC
    CORNER_STYLE_LOOKUP = JOIN_ARC
    MODE = AREA
    OFFSET = 0.1
    OFFSET_UNITS = NONE
    PRECISION = APPROX
    CAP_STYLE = Arc
    CORNER_STYLE = Arc
    BUFFERED -> Clipper [CLIPPER]
Note: Create local area around intersection where the two lines cross.
Clipper
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> LineCombiner
Note: Recombine lines with the same supplier and requestor id
LineCombiner
    ACCUM_ATTRS = ONE
    BREAK_CONNECTION_ATTRIBUTES = Id_requestor Id_supplier
    CLOSE = yes
    CONNECT_Z_MODE_LOOKUP = FIRST_WINS
    CONSIDER_NODE_ELEVATION_LOOKUP = NO
    DEAGGREGATE_GEOMETRY = Deaggregate
    JUNCTIONS_IGNORE_ATTRIBUTES = No
    LINES_AS_SEGMENTS = No
    NODED = END_NODED
    PRESERVE = no
    ACCUM_ATTRS_NAME = Use Attributes From One Feature
    BREAK = no
    CONNECT_Z_MODE = First Wins
    CONSIDER_NODE_ELEVATION = no
    TOPOLOGY = End noded
    LINE -> TestFilter_3
    LINE -> HorizontalAngleCalculator
    LINE -> TestFilter_2
Note: Calculates azimuth
HorizontalAngleCalculator
    ANGLE_TYPE = Feature
    UNIT_OUTPUT = DEG
    -> AttributeRemover
AttributeRemover
    REMOVE_ATTRS = _azimuth,_x,_X,_xEnd,_y,_Y,_yEnd,_z,_zEnd,fme_rejection_code
    -> PointOnLineOverlayer [LINE]
Note: Find the two lines that intersect in the point. Put the azimuth angles of both lines into a list.
PointOnLineOverlayer
    DEAGGREGATE_INPUT = Yes
    LIST_ATTRS_TO_INCLUDE = _angle
    LIST_NAME = angles
    MEASURE_TYPE_LOOKUP = CONTINUOUS
    MERGE_MEASURES = Yes
    OV_ATTR = _overlaps
    TOLERANCE = 0
    MEASURE_TYPE = Continuous
    POINT -> PythonCaller
Note: Calculate the angle delta, which equals the angle at which the tow lines intersect.
PythonCaller
    NEW_ATTRIBUTES = angle_delta
    PYTHONSOURCE:
      import fme
      import fmeobjects


      class FeatureProcessor(object):
          """Template Class Interface:
          When using this class, make sure its name is set as the value of the 'Class
          to Process Features' transformer parameter.
          """

          def __init__(self):
              """Base constructor for class members."""
              pass

          def input(self, feature):
              angle_delta = feature.getAttribute('angles{1}._angle')-feature.getAttribute('angles{0}._angle')
              converted_angle = self.convert_to_0_to_90(angle_delta)
              feature.setAttribute('angle_delta',converted_angle)
              self.pyoutput(feature)

          def convert_to_0_to_90(self,angle):
              # Normalize the angle to be within the range -360 to 360
              normalized_angle = angle % 360

              # Ensure the angle is positive
              if normalized_angle < 0:
                  normalized_angle += 360

              # Convert the angle to the range 0 to 90
              if normalized_angle <= 90:
                  return normalized_angle
              elif normalized_angle <= 180:
                  return 180 - normalized_angle
              elif normalized_angle <= 270:
                  return normalized_angle - 180
              else:
                  return 360 - normalized_angle
    PYTHONSYMBOL = FeatureProcessor
    -> AttributeRemover_2
Note: Remove som unneeded attributes.
AttributeRemover_2
    LIST_ATTRS = angles{}
    REMOVE_ATTRS = Id_requestor,Id_supplier,_overlaps
    -> AttributeRounder
AttributeRounder
    PLACES = $(DECIMAL_PLACES)
    ROUND_TYPE_TCL = round
    SRC_ATTRS = angle_delta
    ROUND_TYPE = Nearest
    -> AttributeRenamer
AttributeRenamer
    ATTR_TABLE = RENAME_SET_DEFAULT angle_delta > angle
    KEEP_RENAMED_ONLY = no
    MISSING_INPUT_ATTRS = REMOVE
    -> IntersectionPoints (output)
IntersectionPoints (output)

Bookmark: Logging of used and unused lines
TestFilter_2
    DEFAULT_VALUE = <UNFILTERED>
    PASSED_TEST_GROUP_OUTPUT = FIRST
    TEST_LIST = "BOOL_OP,OR,COMPOSITE_TEST,""""""1"""""",TEST_CLAUSE,TEST Id_requestor ATTRIBUTE_HAS_A_VALUE """,requestor intersected
    requestor intersected -> DuplicateFilter
DuplicateFilter
    INPUT_ORDERED_CHOICE_LOOKUP = NO
    KEYATTR = Id_requestor
    PRESERVE_FEATURE_ORDER_LOOKUP = PER_OUTPUT_PORT
    INPUT_ORDERED_CHOICE = No
    UNIQUE -> FeatureMerger [SUPPLIER]
Note: Add back the original geometry
FeatureMerger
    ATTR_ACCUM_MODE = Merge Supplier
    ATTR_CONFLICT_RES_LOOKUP = REQUESTOR_IF_CONFLICT
    IGNORE_NULLS = No
    JOIN_KEYS = @Value(Id_requestor) @Value(Id_requestor) AUTO
    MERGE_TYPE_VAL = ATTRIBUTES
    PRESERVE_FEATURE_ORDER_LOOKUP = PER_OUTPUT_PORT
    PROCESS_DUPS = NO
    REJECT_NULL_MISSING_KEYS = No
    SUPPLIERS_FIRST = No
    ATTR_CONFLICT_RES = Use Requestor
    MERGE_TYPE = Attributes Only
    MERGED -> IntersectedRequestor (output)
    UNMERGED_REQUESTOR -> NotIntersectedRequestor (output)
IntersectedRequestor (output)
NotIntersectedRequestor (output)
TestFilter_3
    DEFAULT_VALUE = <UNFILTERED>
    PASSED_TEST_GROUP_OUTPUT = FIRST
    TEST_LIST = "BOOL_OP,OR,COMPOSITE_TEST,""""""1"""""",TEST_CLAUSE,TEST Id_supplier ATTRIBUTE_HAS_A_VALUE """,supplier intersected
    supplier intersected -> DuplicateFilter_2
DuplicateFilter_2
    INPUT_ORDERED_CHOICE_LOOKUP = NO
    KEYATTR = Id_supplier
    PRESERVE_FEATURE_ORDER_LOOKUP = PER_OUTPUT_PORT
    INPUT_ORDERED_CHOICE = No
    UNIQUE -> FeatureMerger_2 [SUPPLIER]
Note: Add back the original geometry
FeatureMerger_2
    ATTR_ACCUM_MODE = Merge Supplier
    ATTR_CONFLICT_RES_LOOKUP = REQUESTOR_IF_CONFLICT
    IGNORE_NULLS = No
    JOIN_KEYS = @Value(Id_supplier) @Value(Id_supplier) AUTO
    MERGE_TYPE_VAL = ATTRIBUTES
    PRESERVE_FEATURE_ORDER_LOOKUP = PER_OUTPUT_PORT
    PROCESS_DUPS = NO
    REJECT_NULL_MISSING_KEYS = No
    SUPPLIERS_FIRST = No
    ATTR_CONFLICT_RES = Use Requestor
    MERGE_TYPE = Attributes Only
    MERGED -> UsedSupplier (output)
    UNMERGED_REQUESTOR -> UnusedSupplier (output)
UsedSupplier (output)
UnusedSupplier (output)

FME custom transformer LoopFilter
Tests whether a line is a loop, i.e. whether start and end coordinates match.
The transformers outputs loops through PASSED port, and non-loops through FAILED port.

LINE (input)
    -> LineFilter
LineFilter: GeometryFilter
    BREAK_AGG_BOOL = 0
    GEOM_PORTS = LINE
    BREAK_AGG = No
    GEOM_PORT_NAMES = Line
    LINE -> CoordinateExtractor
CoordinateExtractor
    IND = 0
    RECURSIVE = No
    X_ATTR = _x1
    Y_ATTR = _y1
    Z_ATTR = _z1
    MODE = Specify Coordinate
    -> CoordinateExtractor_2
CoordinateExtractor_2
    IND = -1
    RECURSIVE = No
    X_ATTR = _x2
    Y_ATTR = _y2
    Z_ATTR = _z2
    MODE = Specify Coordinate
    -> ExpressionEvaluator
ExpressionEvaluator
    ACTION = Create New Attribute
    EXPRESSION = (@Value(_x1)-@Value(_x2))||(@Value(_y1)-@Value(_y2))
    VAL_ATTR = _isLoop
    -> Tester
Tester
    BOOL_OP = OR
    TEST_CLAUSE = TEST @Value(_isLoop) = 0
    TEST_MODE = TEST
    PASSED -> AttributeRemover
    FAILED -> AttributeRemover_2
AttributeRemover
    REMOVE_ATTRS = _z1,_z2,_y1,_y2,_isLoop,_x1,_x2
    -> PASSED (output)
PASSED (output)
AttributeRemover_2
    REMOVE_ATTRS = _z1,_z2,_y1,_y2,_isLoop,_x1,_x2
    -> FAILED (output)
FAILED (output)
