FME workspace 3_2024.fmw

Parameters:
- DestDataset_GEODATABASE_FILE = $(FME_MF_DIR)fme output\3_lijst.gdb   # File Geodatabase

Writers:
- GEODATABASE_FILE_1: GEODATABASE_FILE to $(DestDataset_GEODATABASE_FILE)

Bookmark: 1. Simpele view
SQLCreator
    DATASET = sql_geo
    EXPOSED_ATTRIBUTE_LIST = SHAPE
    FORMAT = MSSQL_SPATIAL
    MSSQL_SPATIAL_APPLICATION_INTENT = ReadWrite
    MSSQL_SPATIAL_COMMAND_TIMEOUT = 30
    MSSQL_SPATIAL_CREATE_FEATURE_TABLES_FROM_DATA = Yes
    MSSQL_SPATIAL_NAMED_CONNECTION = sql_geo
    MSSQL_SPATIAL_QUERY_FEATURE_TYPES_FOR_MERGE_FILTERS = Yes
    OUTPUT_FEATURES = BASED_ON_CONNECTIONS
    SQL_STATEMENT:
      SELECT t.*
      FROM TOPOGRAFIE.BAG_PAND_PZH t
      WHERE GEBR_WOONFUNCTIE = 1
        AND EXISTS (
          SELECT 1
          FROM GRENZEN.GEMEENTE_VLAK_2022 g
          WHERE g.GEMEENTE = 'Hendrik-Ido-Ambacht'
            AND t.SHAPE.STIntersects(g.SHAPE) = 1
        );
    RESULT -> GeometryReplacer
GeometryReplacer
    KIND = mssql
    MSSQL_FORMAT = geometry
    REMOVE_ATTRIBUTE = Yes
    SOURCE = @Value(SHAPE)
    KIND_LONG = Microsoft SQL Server Binary
    MSSQL_FORMAT_CHOICE = Geometry
SQLCreator_2
    DATASET = sql_geo
    EXPOSED_ATTRIBUTE_LIST = SHAPE
    FORMAT = MSSQL_SPATIAL
    MSSQL_SPATIAL_APPLICATION_INTENT = ReadWrite
    MSSQL_SPATIAL_COMMAND_TIMEOUT = 30
    MSSQL_SPATIAL_CREATE_FEATURE_TABLES_FROM_DATA = Yes
    MSSQL_SPATIAL_NAMED_CONNECTION = sql_geo
    MSSQL_SPATIAL_QUERY_FEATURE_TYPES_FOR_MERGE_FILTERS = Yes
    OUTPUT_FEATURES = BASED_ON_CONNECTIONS
    SQL_STATEMENT:
      WITH gemeente_geom AS (
        SELECT SHAPE
        FROM GRENZEN.GEMEENTE_VLAK_2022
        WHERE GEMEENTE = 'Hendrik-Ido-Ambacht'
      ),

      bomen_in_gemeente AS (
        SELECT top 1000 b.*
        FROM BODEM.BOMEN_KRONEN b
        JOIN gemeente_geom g
          ON b.SHAPE.STIntersects(g.SHAPE) = 1
      ),

      bomen_buffer AS (
        SELECT b.*, b.SHAPE.STBuffer(25) AS buffer_geom
        FROM bomen_in_gemeente b
      )

      SELECT p.*
      FROM TOPOGRAFIE.BAG_PAND_PZH p
      JOIN gemeente_geom g
        ON p.SHAPE.STIntersects(g.SHAPE) = 1
      JOIN bomen_buffer bb
        ON p.SHAPE.STIntersects(bb.buffer_geom) = 1
      WHERE p.GEBR_WOONFUNCTIE = 1;
    RESULT -> GeometryReplacer_2
GeometryReplacer_2
    KIND = mssql
    MSSQL_FORMAT = geometry
    REMOVE_ATTRIBUTE = Yes
    SOURCE = @Value(SHAPE)
    KIND_LONG = Microsoft SQL Server Binary
    MSSQL_FORMAT_CHOICE = Geometry

Bookmark: 2. Huizen than intersecten met de 25 m buffer van bomen die hoger zijn dan 3 meter., -
Creator
    GEOMTYPE = Geometry Object
    NUM = 1
    CREATED -> FeatureReader [INITIATOR]
FeatureReader
    ATTRIBUTES =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
    ATTR_ACCUM_MODE = Only Use Result
    COMBINE_GEOM = Use Result
    DATASET = $(FME_MF_DIR_ENCODED)fme input\Panden\wijkenbuurten_2023.gpkg
    FEATURETYPES = wijken
    FORMAT = OGCGEOPACKAGE
    GEOMETRY_TYPES = buurten,""",fme_area""",gemeenten,""",fme_area""",wijken,""",fme_area"""
    INTERACT = NONE
    OGCGEOPACKAGE_ENCODE_FEATURE_TYPE_AND_ATTR_NAMES = YES
    OGCGEOPACKAGE_ENFORCE_FOREIGN_KEY_INTEGRITY = YES
    OGCGEOPACKAGE_EXPOSE_PRIMARY_KEY_ATTRIBUTE = YES
    OGCGEOPACKAGE_OPEN_SINGLE_RASTER_AS_SUBDATASET = YES
    OGCGEOPACKAGE_QUERY_FEATURE_TYPES_FOR_MERGE_FILTERS = Yes
    OGCGEOPACKAGE_READER_REPLACE_INVALID_CHARS = NO
    OGCGEOPACKAGE_READ_BOOLEANS_AS_YES_NO = YES
    OGCGEOPACKAGE_READ_NULLS = YES
    OGCGEOPACKAGE_USE_SEARCH_ENVELOPE = NO
    ORDER_RESULTS = No
    OUTPUT_ADD_SCHEMA_ATTRIBUTES = NO
    OUTPUT_FEATURES_DISPLAY = Schema and Data Features
    WHERE = "gemeentenaam"='Hendrik-Ido-Ambacht'
    wijken -> SQLExecutor [INITIATOR]
SQLExecutor
    COMBINE_ATTRS = Result Attributes Only
    COMBINE_GEOM = Result Geometry Only
    DATASET = sql_geo
    EXPOSED_ATTRIBUTE_LIST = SHAPE
    FORMAT = MSSQL_SPATIAL
    MSSQL_SPATIAL_APPLICATION_INTENT = ReadWrite
    MSSQL_SPATIAL_COMMAND_TIMEOUT = 200
    MSSQL_SPATIAL_CREATE_FEATURE_TABLES_FROM_DATA = Yes
    MSSQL_SPATIAL_NAMED_CONNECTION = sql_geo
    MSSQL_SPATIAL_QUERY_FEATURE_TYPES_FOR_MERGE_FILTERS = Yes
    OUTPUT_FEATURES = DATA_ONLY
    SQL_STATEMENT:
      WITH gemeente_geom AS (
        SELECT SHAPE AS gemeente_shape
        FROM GRENZEN.CBS_WIJKKAART_2022_VERSIE3
        WHERE wijkcode = 'WK053101'
      ),

      bomen_in_buffer AS (
        SELECT
          b.OBJECTID AS boom_id,
          b.SHAPE.STBuffer(25) AS buffer_geom
        FROM BODEM.BOMEN_CENTERPOINTS b
        JOIN gemeente_geom g ON b.SHAPE.STIntersects(g.gemeente_shape) = 1
      ),

      panden_in_buffer AS (
        SELECT DISTINCT p.OBJECTID AS pand_id
        FROM TOPOGRAFIE.BAG_PAND_PZH p
        JOIN gemeente_geom g ON p.SHAPE.STIntersects(g.gemeente_shape) = 1
        JOIN bomen_in_buffer b ON p.SHAPE.STIntersects(b.buffer_geom) = 1
        WHERE p.GEBR_WOONFUNCTIE = 1
      )

      SELECT p.OBJECTID
      FROM TOPOGRAFIE.BAG_PAND_PZH p
      JOIN panden_in_buffer pb ON p.OBJECTID = pb.pand_id;
    RESULT -> GeometryReplacer_3
GeometryReplacer_3
    KIND = mssql
    MSSQL_FORMAT = geometry
    REMOVE_ATTRIBUTE = Yes
    SOURCE = @Value(SHAPE)
    KIND_LONG = Microsoft SQL Server Binary
    MSSQL_FORMAT_CHOICE = Geometry

Bookmark: 3. Huizen that intersecten met de 25 m buffer van bomen, met attribut nummer of overlaps., (ObjectID is pandid) - 3'6"
Creator_2
    GEOMTYPE = Geometry Object
    NUM = 1
    CREATED -> FeatureReader_2 [INITIATOR]
FeatureReader_2
    ATTRIBUTES =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
    ATTR_ACCUM_MODE = Only Use Result
    COMBINE_GEOM = Use Result
    DATASET = $(FME_MF_DIR_ENCODED)fme input\Panden\wijkenbuurten_2023.gpkg
    FEATURETYPES = wijken
    FORMAT = OGCGEOPACKAGE
    GEOMETRY_TYPES = buurten,""",fme_area""",gemeenten,""",fme_area""",wijken,""",fme_area"""
    INTERACT = NONE
    OGCGEOPACKAGE_ENCODE_FEATURE_TYPE_AND_ATTR_NAMES = YES
    OGCGEOPACKAGE_ENFORCE_FOREIGN_KEY_INTEGRITY = YES
    OGCGEOPACKAGE_EXPOSE_PRIMARY_KEY_ATTRIBUTE = YES
    OGCGEOPACKAGE_OPEN_SINGLE_RASTER_AS_SUBDATASET = YES
    OGCGEOPACKAGE_QUERY_FEATURE_TYPES_FOR_MERGE_FILTERS = Yes
    OGCGEOPACKAGE_READER_REPLACE_INVALID_CHARS = NO
    OGCGEOPACKAGE_READ_BOOLEANS_AS_YES_NO = YES
    OGCGEOPACKAGE_READ_NULLS = YES
    OGCGEOPACKAGE_USE_SEARCH_ENVELOPE = NO
    ORDER_RESULTS = No
    OUTPUT_ADD_SCHEMA_ATTRIBUTES = NO
    OUTPUT_FEATURES_DISPLAY = Schema and Data Features
    WHERE = "gemeentenaam"='Hendrik-Ido-Ambacht'
    wijken -> SQLExecutor_2 [INITIATOR]
SQLExecutor_2
    COMBINE_ATTRS = Result Attributes Only
    COMBINE_GEOM = Result Geometry Only
    DATASET = sql_geo
    FORMAT = MSSQL_SPATIAL
    MSSQL_SPATIAL_APPLICATION_INTENT = ReadWrite
    MSSQL_SPATIAL_COMMAND_TIMEOUT = 100
    MSSQL_SPATIAL_CREATE_FEATURE_TABLES_FROM_DATA = Yes
    MSSQL_SPATIAL_NAMED_CONNECTION = sql_geo
    MSSQL_SPATIAL_QUERY_FEATURE_TYPES_FOR_MERGE_FILTERS = Yes
    OUTPUT_FEATURES = DATA_ONLY
    SQL_STATEMENT:
      WITH gemeente_geom AS (
        SELECT SHAPE.STBuffer(25) AS SHAPE
        FROM [GRENZEN].[CBS_WIJKKAART_2022_VERSIE3]
        WHERE wijkcode = '@Value(wijkcode)'
      ),

      bomen_in_gemeente AS (
        SELECT b.OBJECTID AS boom_id, b.SHAPE.STBuffer(25) AS buffer_geom
        FROM BODEM.BOMEN_CENTERPOINTS b
        JOIN gemeente_geom g
          ON b.SHAPE.Filter(g.SHAPE) = 1
          AND b.SHAPE.STIntersects(g.SHAPE) = 1
      ),

      boom_pand_match AS (
        SELECT
          b.boom_id,
          p.OBJECTID AS pand_id
        FROM bomen_in_gemeente b
        JOIN TOPOGRAFIE.BAG_PAND_PZH p
          ON p.SHAPE.Filter(b.buffer_geom) = 1
          AND p.SHAPE.STIntersects(b.buffer_geom) = 1
        WHERE p.GEBR_WOONFUNCTIE = 1
      )

      SELECT
        p.OBJECTID,
        COUNT(bpm.boom_id) AS overlaps,
        STRING_AGG(CAST(bpm.boom_id AS NVARCHAR), ',') AS boom_ids
      FROM TOPOGRAFIE.BAG_PAND_PZH p
      LEFT JOIN boom_pand_match bpm
        ON p.OBJECTID = bpm.pand_id
      JOIN gemeente_geom g
        ON p.SHAPE.Filter(g.SHAPE) = 1
        AND p.SHAPE.STIntersects(g.SHAPE) = 1
      WHERE p.GEBR_WOONFUNCTIE = 1
      GROUP BY p.OBJECTID;
    RESULT -> Relaties (writer GEODATABASE_FILE_1)
Relaties (writer GEODATABASE_FILE_1)

Bookmark: 4. Huizen that intersecten met de 25m buffer, sightlines meegenomen. Deze zijn individueel, dus nog niet multiple lines - 8'41" voor een wijk . Todo: subset >3m in een aparte laag
Creator_3
    GEOMTYPE = Geometry Object
    NUM = 1
    CREATED -> FeatureReader_3 [INITIATOR]
FeatureReader_3
    ATTRIBUTES =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
    ATTR_ACCUM_MODE = Only Use Result
    COMBINE_GEOM = Use Result
    DATASET = $(FME_MF_DIR_ENCODED)fme input\Panden\wijkenbuurten_2023.gpkg
    FEATURETYPES = wijken
    FORMAT = OGCGEOPACKAGE
    GEOMETRY_TYPES = buurten,""",fme_area""",gemeenten,""",fme_area""",wijken,""",fme_area"""
    INTERACT = NONE
    OGCGEOPACKAGE_ENCODE_FEATURE_TYPE_AND_ATTR_NAMES = YES
    OGCGEOPACKAGE_ENFORCE_FOREIGN_KEY_INTEGRITY = YES
    OGCGEOPACKAGE_EXPOSE_PRIMARY_KEY_ATTRIBUTE = YES
    OGCGEOPACKAGE_OPEN_SINGLE_RASTER_AS_SUBDATASET = YES
    OGCGEOPACKAGE_QUERY_FEATURE_TYPES_FOR_MERGE_FILTERS = Yes
    OGCGEOPACKAGE_READER_REPLACE_INVALID_CHARS = NO
    OGCGEOPACKAGE_READ_BOOLEANS_AS_YES_NO = YES
    OGCGEOPACKAGE_READ_NULLS = YES
    OGCGEOPACKAGE_USE_SEARCH_ENVELOPE = NO
    ORDER_RESULTS = No
    OUTPUT_ADD_SCHEMA_ATTRIBUTES = NO
    OUTPUT_FEATURES_DISPLAY = Schema and Data Features
    WHERE = "gemeentenaam"='Hendrik-Ido-Ambacht'
    wijken -> Sampler_2
Sampler_2
    MODE = ORIGINAL
    RATE = 1
    SAMPLE_TYPE_MULTIPLIER = -1
    SAMPLE_MODE = No
    SAMPLE_TYPE_LONG = First N Features
    SAMPLED -> SQLExecutor_3 [INITIATOR]
    SAMPLED -> FeatureReader_4 [INITIATOR]
SQLExecutor_3
    COMBINE_ATTRS = Result Attributes Only
    COMBINE_GEOM = Result Geometry Only
    DATASET = sql_geo
    EXPOSED_ATTRIBUTE_LIST = SHAPE
    FORMAT = MSSQL_SPATIAL
    MSSQL_SPATIAL_APPLICATION_INTENT = ReadWrite
    MSSQL_SPATIAL_COMMAND_TIMEOUT = 30
    MSSQL_SPATIAL_CREATE_FEATURE_TABLES_FROM_DATA = Yes
    MSSQL_SPATIAL_NAMED_CONNECTION = sql_geo
    MSSQL_SPATIAL_QUERY_FEATURE_TYPES_FOR_MERGE_FILTERS = Yes
    OUTPUT_FEATURES = DATA_ONLY
    SQL_STATEMENT:
      -- Define buffered wijk
      WITH wijk_geom AS (
        SELECT SHAPE.STBuffer(25) AS wijk_buffer_geom
        FROM GRENZEN.CBS_WIJKKAART_2022_VERSIE3
        WHERE wijkcode = '@Value(wijkcode)'
      ),

      -- Select relevant trees
      bomen_in_wijk AS (
        SELECT b.OBJECTID AS boom_id, b.SHAPE
        FROM BODEM.BOMEN_KRONEN b
        JOIN wijk_geom w ON b.SHAPE.STIntersects(w.wijk_buffer_geom) = 1
      ),

      -- Select residential buildings in buffer
      panden_in_wijk AS (
        SELECT p.OBJECTID AS pand_id, p.SHAPE
        FROM TOPOGRAFIE.BAG_PAND_PZH p
        JOIN wijk_geom w ON p.SHAPE.STIntersects(w.wijk_buffer_geom) = 1
        WHERE p.GEBR_WOONFUNCTIE = 1
      )

      -- Final: Generate line segments and return base info
      SELECT
        p.pand_id,
        b.boom_id,
        geometry::STLineFromText('LINESTRING(' +
            CAST(p.SHAPE.STExteriorRing().STPointN(1).STX AS VARCHAR(20)) + ' ' +
            CAST(p.SHAPE.STExteriorRing().STPointN(1).STY AS VARCHAR(20)) + ',' +
            CAST(b.SHAPE.STCentroid().STX AS VARCHAR(20)) + ' ' +
            CAST(b.SHAPE.STCentroid().STY AS VARCHAR(20)) + ')', 28992
        ) AS sightline
      FROM panden_in_wijk p
      JOIN bomen_in_wijk b
        ON p.SHAPE.STDistance(b.SHAPE) <= 25;
    RESULT -> AttributeExposer
AttributeExposer
    ATTR_TABLE = sightline,
    -> GeometryReplacer_5
GeometryReplacer_5
    KIND = mssql
    MSSQL_FORMAT = geometry
    REMOVE_ATTRIBUTE = Yes
    SOURCE = @Value(sightline)
    KIND_LONG = Microsoft SQL Server Binary
    MSSQL_FORMAT_CHOICE = Geometry
    -> Sightlines
Sightlines: Inspector
FeatureReader_4
    ATTRIBUTES = BODEM.BOMEN_CENTERPOINTS,"OBJECTID,id,stem_id,tree_id,sys_period,dataset,date,method,quality,accuracy,accuracy_metadata,transaction_id,current_status,status_date",BODEM.BOMEN_KRONEN,"OBJECTID,id,tree_id,valid_period,sys_period,tile_name,current_status,status_date,status_source_id,management_form,management_form_dataset,management_form_date,management_form_method,management_form_quality,crown_area,crown_diameter,crown_dataset,crown_date,crown_method,crown_quality,height,height_dataset,height_date,height_method,height_quality,undergrowth_cover,undergrowth_dataset,undergrowth_date,undergrowth_method,undergrowth_quality,Geo_afgeschermd.BODEM.BOMEN_KRONEN.fid,Shape.STArea(),Shape.STLength()"
    ATTR_ACCUM_MODE = Only Use Result
    COMBINE_GEOM = Use Result
    DATASET = bomen
    FEATURETYPES = BODEM.BOMEN_CENTERPOINTS BODEM.BOMEN_KRONEN
    FORMAT = GEODATABASE_SDE
    GEODATABASE_SDE_ALIAS_MODE = NONE
    GEODATABASE_SDE_CACHE_MULTIPATCH_TEXTURES = yes
    GEODATABASE_SDE_CHECK_SIMPLE_GEOM = no
    GEODATABASE_SDE_CREATE_FEATURE_TABLES_FROM_DATA = Yes
    GEODATABASE_SDE_DISABLE_FEATURE_DATASET_ATTRIBUTE = Yes
    GEODATABASE_SDE_FEATURE_READ_MODE = Features
    GEODATABASE_SDE_IGNORE_NETWORK_INFO = yes
    GEODATABASE_SDE_IGNORE_RELATIONSHIP_INFO = yes
    GEODATABASE_SDE_MERGE_FEAT_LINKED_ANNOS = no
    GEODATABASE_SDE_NAMED_CONNECTION = bomen
    GEODATABASE_SDE_PERSISTENT_CONNECTION = no
    GEODATABASE_SDE_QUERY_FEATURE_TYPES_FOR_MERGE_FILTERS = Yes
    GEODATABASE_SDE_READ_THREE_POINT_ARCS = no
    GEODATABASE_SDE_READ_VERSION_DIFFERENCES = NO
    GEODATABASE_SDE_REMOVE_FEATURE_DATASET = NO
    GEODATABASE_SDE_REMOVE_TABLE_QUALIFIER = NO
    GEODATABASE_SDE_RESOLVE_DOMAINS = no
    GEODATABASE_SDE_RESOLVE_SUBTYPE_NAMES = yes
    GEODATABASE_SDE_SIMPLE_DONUT_GEOMETRY = no
    GEODATABASE_SDE_SPLIT_COMPLEX_ANNOS = no
    GEODATABASE_SDE_SPLIT_COMPLEX_EDGES = no
    GEODATABASE_SDE_SPLIT_MULTI_PART_ANNOS = no
    GEODATABASE_SDE_STRIP_GUID_GLOBALID_BRACES = no
    GEODATABASE_SDE_TRANSLATE_SPATIAL_DATA_ONLY = no
    GEODATABASE_SDE_USE_SEARCH_ENVELOPE = NO
    GEOMETRY_TYPES = BODEM.BOMEN_CENTERPOINTS,""",fme_point""",BODEM.BOMEN_KRONEN,""",fme_area"""
    INTERACT = INTERSECTS
    ORDER_RESULTS = No
    OUTPUT_ADD_SCHEMA_ATTRIBUTES = NO
    OUTPUT_FEATURES_DISPLAY = Schema and Data Features
    BODEM.BOMEN_CENTERPOINTS -> FeatureReader_4_BODEM.BOMEN_CENTERPOINTS
    BODEM.BOMEN_KRONEN -> FeatureReader_4_BODEM.BOMEN_KRONEN
FeatureReader_4_BODEM.BOMEN_CENTERPOINTS: Inspector
FeatureReader_4_BODEM.BOMEN_KRONEN: Inspector

Bookmark: Meerdere zichtlijnen - time out
Creator_4
    GEOMTYPE = Geometry Object
    NUM = 1
    CREATED -> FeatureReader_5 [INITIATOR]
FeatureReader_5
    ATTRIBUTES =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
    ATTR_ACCUM_MODE = Only Use Result
    COMBINE_GEOM = Use Result
    DATASET = $(FME_MF_DIR_ENCODED)fme input\Panden\wijkenbuurten_2023.gpkg
    FEATURETYPES = wijken
    FORMAT = OGCGEOPACKAGE
    GEOMETRY_TYPES = buurten,""",fme_area""",gemeenten,""",fme_area""",wijken,""",fme_area"""
    INTERACT = NONE
    OGCGEOPACKAGE_ENCODE_FEATURE_TYPE_AND_ATTR_NAMES = YES
    OGCGEOPACKAGE_ENFORCE_FOREIGN_KEY_INTEGRITY = YES
    OGCGEOPACKAGE_EXPOSE_PRIMARY_KEY_ATTRIBUTE = YES
    OGCGEOPACKAGE_OPEN_SINGLE_RASTER_AS_SUBDATASET = YES
    OGCGEOPACKAGE_QUERY_FEATURE_TYPES_FOR_MERGE_FILTERS = Yes
    OGCGEOPACKAGE_READER_REPLACE_INVALID_CHARS = NO
    OGCGEOPACKAGE_READ_BOOLEANS_AS_YES_NO = YES
    OGCGEOPACKAGE_READ_NULLS = YES
    OGCGEOPACKAGE_USE_SEARCH_ENVELOPE = NO
    ORDER_RESULTS = No
    OUTPUT_ADD_SCHEMA_ATTRIBUTES = NO
    OUTPUT_FEATURES_DISPLAY = Schema and Data Features
    WHERE = "gemeentenaam"='Hendrik-Ido-Ambacht'
    wijken -> Sampler_3
Sampler_3
    MODE = ORIGINAL
    RATE = 1
    SAMPLE_TYPE_MULTIPLIER = -1
    SAMPLE_MODE = No
    SAMPLE_TYPE_LONG = First N Features
    SAMPLED -> SQLExecutor_4 [INITIATOR]
    SAMPLED -> FeatureReader_6 [INITIATOR]
SQLExecutor_4
    COMBINE_ATTRS = Result Attributes Only
    COMBINE_GEOM = Result Geometry Only
    DATASET = sql_geo
    EXPOSED_ATTRIBUTE_LIST = SHAPE
    FORMAT = MSSQL_SPATIAL
    MSSQL_SPATIAL_APPLICATION_INTENT = ReadWrite
    MSSQL_SPATIAL_COMMAND_TIMEOUT = 30
    MSSQL_SPATIAL_CREATE_FEATURE_TABLES_FROM_DATA = Yes
    MSSQL_SPATIAL_NAMED_CONNECTION = sql_geo
    MSSQL_SPATIAL_QUERY_FEATURE_TYPES_FOR_MERGE_FILTERS = Yes
    OUTPUT_FEATURES = DATA_ONLY
    SQL_STATEMENT:
      WITH ... -- buffer, panden, tree centroids

      SELECT TOP 3 WITH TIES
        b.tree_id,
        p.pand_id,
        v.vertex_geom,
        b.SHAPE.STCentroid().STDistance(v.vertex_geom) AS dist
      FROM bomen_buffer b
      JOIN panden_vertices v
        ON b.buffer_geom.STIntersects(v.vertex_geom) = 1
      JOIN panden p
        ON v.pand_id = p.pand_id
      ORDER BY
        ROW_NUMBER() OVER (PARTITION BY b.tree_id, v.pand_id ORDER BY dist)
    RESULT -> AttributeExposer_2
AttributeExposer_2
    ATTR_TABLE = line_outside_pand,
    -> GeometryReplacer_6
GeometryReplacer_6
    KIND = mssql
    MSSQL_FORMAT = geometry
    REMOVE_ATTRIBUTE = Yes
    SOURCE = @Value(line_outside_pand)
    KIND_LONG = Microsoft SQL Server Binary
    MSSQL_FORMAT_CHOICE = Geometry
    -> Sightlines_2
Sightlines_2: Inspector
FeatureReader_6
    ATTRIBUTES = BODEM.BOMEN_CENTERPOINTS,"OBJECTID,id,stem_id,tree_id,sys_period,dataset,date,method,quality,accuracy,accuracy_metadata,transaction_id,current_status,status_date",BODEM.BOMEN_KRONEN,"OBJECTID,id,tree_id,valid_period,sys_period,tile_name,current_status,status_date,status_source_id,management_form,management_form_dataset,management_form_date,management_form_method,management_form_quality,crown_area,crown_diameter,crown_dataset,crown_date,crown_method,crown_quality,height,height_dataset,height_date,height_method,height_quality,undergrowth_cover,undergrowth_dataset,undergrowth_date,undergrowth_method,undergrowth_quality,Geo_afgeschermd.BODEM.BOMEN_KRONEN.fid,Shape.STArea(),Shape.STLength()"
    ATTR_ACCUM_MODE = Only Use Result
    COMBINE_GEOM = Use Result
    DATASET = bomen
    FEATURETYPES = BODEM.BOMEN_CENTERPOINTS BODEM.BOMEN_KRONEN
    FORMAT = GEODATABASE_SDE
    GEODATABASE_SDE_ALIAS_MODE = NONE
    GEODATABASE_SDE_CACHE_MULTIPATCH_TEXTURES = yes
    GEODATABASE_SDE_CHECK_SIMPLE_GEOM = no
    GEODATABASE_SDE_CREATE_FEATURE_TABLES_FROM_DATA = Yes
    GEODATABASE_SDE_DISABLE_FEATURE_DATASET_ATTRIBUTE = Yes
    GEODATABASE_SDE_FEATURE_READ_MODE = Features
    GEODATABASE_SDE_IGNORE_NETWORK_INFO = yes
    GEODATABASE_SDE_IGNORE_RELATIONSHIP_INFO = yes
    GEODATABASE_SDE_MERGE_FEAT_LINKED_ANNOS = no
    GEODATABASE_SDE_NAMED_CONNECTION = bomen
    GEODATABASE_SDE_PERSISTENT_CONNECTION = no
    GEODATABASE_SDE_QUERY_FEATURE_TYPES_FOR_MERGE_FILTERS = Yes
    GEODATABASE_SDE_READ_THREE_POINT_ARCS = no
    GEODATABASE_SDE_READ_VERSION_DIFFERENCES = NO
    GEODATABASE_SDE_REMOVE_FEATURE_DATASET = NO
    GEODATABASE_SDE_REMOVE_TABLE_QUALIFIER = NO
    GEODATABASE_SDE_RESOLVE_DOMAINS = no
    GEODATABASE_SDE_RESOLVE_SUBTYPE_NAMES = yes
    GEODATABASE_SDE_SIMPLE_DONUT_GEOMETRY = no
    GEODATABASE_SDE_SPLIT_COMPLEX_ANNOS = no
    GEODATABASE_SDE_SPLIT_COMPLEX_EDGES = no
    GEODATABASE_SDE_SPLIT_MULTI_PART_ANNOS = no
    GEODATABASE_SDE_STRIP_GUID_GLOBALID_BRACES = no
    GEODATABASE_SDE_TRANSLATE_SPATIAL_DATA_ONLY = no
    GEODATABASE_SDE_USE_SEARCH_ENVELOPE = NO
    GEOMETRY_TYPES = BODEM.BOMEN_CENTERPOINTS,""",fme_point""",BODEM.BOMEN_KRONEN,""",fme_area"""
    INTERACT = INTERSECTS
    ORDER_RESULTS = No
    OUTPUT_ADD_SCHEMA_ATTRIBUTES = NO
    OUTPUT_FEATURES_DISPLAY = Schema and Data Features
    BODEM.BOMEN_CENTERPOINTS -> FeatureReader_4_BODEM.BOMEN_CENTERPOINTS_2
    BODEM.BOMEN_KRONEN -> FeatureReader_4_BODEM.BOMEN_KRONEN_2
FeatureReader_4_BODEM.BOMEN_CENTERPOINTS_2: Inspector
FeatureReader_4_BODEM.BOMEN_KRONEN_2: Inspector
