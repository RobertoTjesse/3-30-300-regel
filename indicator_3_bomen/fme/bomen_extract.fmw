FME workspace bomen_extract.fmw

Parameters:
- SourceDataset_GEODATABASE_SDE = arc_user   # ArcSDE Geodatabase Connection
- SourceDataset_OGCGEOPACKAGE = $(FME_MF_DIR)fme input\gemeentes\Gemeentes_2022.gpkg   # GeoPackage File
- DestDataset_SHAPEFILE = $(FME_MF_DIR)fme input\bomen   # Destination Esri Shapefile Folder

Readers:
- GEODATABASE_SDE_1: GEODATABASE_SDE from $(SourceDataset_GEODATABASE_SDE)
- OGCGEOPACKAGE_1: OGCGEOPACKAGE from $(SourceDataset_OGCGEOPACKAGE)

Writers:
- SHAPEFILE_1: SHAPEFILE to $(DestDataset_SHAPEFILE)

BOMEN_CENTERPOINTS (reader GEODATABASE_SDE_1)
    attributes: OBJECTID integer, id integer, stem_id char(1073741822), tree_id char(1073741822), sys_period char(1073741822), dataset char(1073741822), date date, method char(1073741822), quality double, accuracy double, accuracy_metadata char(1073741822), transaction_id integer, current_status char(2048), status_date date
    -> SpatialRelator [Requestor]
bestuurlijkegebieden_2022__gemeentegebied (reader OGCGEOPACKAGE_1)
    attributes: identificatie text, naam text, code text, ligt_in_provincie_code text, ligt_in_provincie_naam text, fid int,PrimaryKey
    -> SpatialRelator [Supplier]
SpatialRelator
    AGGREGATE_HANDLING = Yes
    ATTR_ACCUM_MODE = Merge Supplier
    ATTR_CONFLICT_RES = Use Requestor
    CALC_CARD = No
    CURVE_BOUNDARY_RULE_PARAM = Default Rule
    IGNORE_NULLS = Yes
    LIST_NAME = _relationships
    PREDICATES = WITHIN
    SUCCESS_ATTR = _related_suppliers
    -> Shapefile1 (writer SHAPEFILE_1)
Shapefile1 (writer SHAPEFILE_1)
    attributes: OBJECTID long, id long, stem_id varchar(1073741822), tree_id varchar(1073741822), sys_period varchar(1073741822), dataset varchar(1073741822), date datetime, method varchar(1073741822), quality double, accuracy double, accuracy_m varchar(1073741822), transactio long, current_st varchar(2048), status_dat datetime, identifica varchar(254), naam varchar(254), code varchar(254), ligt_in_pr varchar(254), ligt_in_00 varchar(254), fid number(20,0), Q__relatio varchar(254), Q__relat00 varchar(254), Q__related double
